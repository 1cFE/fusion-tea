package integrated_equipment_parts {
    private import costed_component::*;
    part def 'Selected Equipment' :> 'Costed Component' {
        doc /* **Source**: work/active/WI-090_aries-integrated-equipment-and-costs/design.md. **Ref**: accepted equations, variable-role table and assumptions E1-E10; source-basis.md linked there. **Basis**: [ASSUMED] conditional engineering estimate, USD2004. **Last Updated**: 2026-09-22. */
    }
}
