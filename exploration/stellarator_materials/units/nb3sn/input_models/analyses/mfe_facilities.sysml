package mfe_facilities {
    private import ScalarValues::*;
    calc def 'Facility Layout' {
        doc /* Source: work/active/WI-068_layout-based-facilities/design.md; layout-capacity-design.md; evidence/facility-contract.md. Ref: released geometry, capacity, exact civil takeoff and account boundary. Basis: conditional conceptual scenario; unqualified shielding/loading/transport and explicit provisional equipment envelopes. Manual completion reuses the live calendar and emits the declared finite scalar contract; deterministic ledgers are diagnostics. */
        in attribute facilities_enabled_in : Boolean default := false;
        in attribute facilities_cost_mode_in : Real default := 0.0;
        in attribute sector_count_in : Real default := 4.0;
        in attribute sector_bays_in : Real default := 4.0;
        in attribute sector_service_teams_in : Real default := 2.0;
        in attribute exterior_allowance_in : Real default := 2.0;
        in attribute sector_route_clearance_in : Real default := 6.0;
        in attribute sector_headroom_in : Real default := 3.0;
        in attribute component_width_in : Real default := 4.0;
        in attribute component_height_in : Real default := 2.0;
        in attribute component_length_in : Real default := 2.0;
        in attribute component_handling_margin_in : Real default := 0.5;
        in attribute component_material_fraction_in : Real default := 0.5;
        in attribute divertor_packages_per_sector_in : Real default := 4.0;
        in attribute waste_package_yield_in : Real default := 1.0;
        in attribute component_remove_days_in : Real default := 0.5;
        in attribute component_install_days_in : Real default := 0.5;
        in attribute sector_clean_days_in : Real default := 7.0;
        in attribute sector_test_days_in : Real default := 7.0;
        in attribute sector_split_days_in : Real default := 7.0;
        in attribute sector_join_days_in : Real default := 7.0;
        in attribute sector_transport_days_in : Real default := 2.0;
        in attribute cooldown_days_in : Real default := 30.0;
        in attribute recommission_days_in : Real default := 30.0;
        in attribute initial_receipt_lead_days_in : Real default := 180.0;
        in attribute initial_sector_start_days_in : Real default := -120.0;
        in attribute component_receipt_lead_days_in : Real default := 90.0;
        in attribute component_prepare_days_in : Real default := 1.0;
        in attribute component_process_days_in : Real default := 1.0;
        in attribute component_hold_days_in : Real default := 365.25;
        in attribute clean_positions_in : Real default := 36.0;
        in attribute dirty_buffer_positions_in : Real default := 18.0;
        in attribute dirty_store_positions_in : Real default := 36.0;
        in attribute cooling_initial_receipt_lead_days_in : Real default := 180.0;
        in attribute cooling_initial_handoff_days_in : Real default := -30.0;
        in attribute cooling_receipt_lead_days_in : Real default := 90.0;
        in attribute cooling_hold_days_in : Real default := 365.25;
        in attribute cooling_prepare_stations_in : Real default := 2.0;
        in attribute cooling_machine_stations_in : Real default := 2.0;
        in attribute cooling_bundle_stations_in : Real default := 2.0;
        in attribute cooling_prepare_machine_days_in : Real default := 0.5;
        in attribute cooling_prepare_bundle_days_in : Real default := 1.0;
        in attribute cooling_machine_process_days_in : Real default := 2.0;
        in attribute cooling_bundle_process_days_in : Real default := 5.0;
        in attribute cooling_field_cycle_days_in : Real default := 0.2;
        in attribute cooling_internal_move_days_in : Real default := 0.1;
        in attribute cooling_clean_helium_positions_in : Real default := 29.0;
        in attribute cooling_clean_salt_positions_in : Real default := 29.0;
        in attribute cooling_clean_bundle_positions_in : Real default := 14.0;
        in attribute cooling_dirty_helium_positions_in : Real default := 28.0;
        in attribute cooling_dirty_salt_positions_in : Real default := 28.0;
        in attribute cooling_dirty_bundle_positions_in : Real default := 14.0;
        in attribute helium_package_length_in : Real default := 6.0;
        in attribute helium_package_width_in : Real default := 3.0;
        in attribute helium_package_height_in : Real default := 4.0;
        in attribute salt_package_length_in : Real default := 3.0;
        in attribute salt_package_width_in : Real default := 2.0;
        in attribute salt_package_height_in : Real default := 3.0;
        in attribute hx_end_allowance_in : Real default := 2.0;
        in attribute cooling_package_margin_in : Real default := 1.0;
        in attribute cooling_aisle_width_in : Real default := 6.0;
        in attribute cooling_cross_width_in : Real default := 17.0;
        in attribute cooling_headroom_in : Real default := 9.0;
        in attribute cooling_airlock_length_in : Real default := 17.0;
        in attribute nuclear_wall_in : Real default := 2.0;
        in attribute nuclear_floor_in : Real default := 1.0;
        in attribute nuclear_roof_in : Real default := 1.0;
        in attribute nuclear_rebar_density_in : Real default := 150.0;
        in attribute conventional_wall_in : Real default := 0.3;
        in attribute conventional_floor_in : Real default := 0.3;
        in attribute conventional_roof_in : Real default := 0.2;
        in attribute conventional_rebar_density_in : Real default := 100.0;
        in attribute building_separation_in : Real default := 10.0;
        in attribute external_access_width_in : Real default := 12.0;
        in attribute provisional_envelope_scale_in : Real default := 1.0;
        in attribute administration_occupants_in : Real default := 200.0;
        in attribute control_occupants_in : Real default := 30.0;
        in attribute security_occupants_in : Real default := 10.0;
        in attribute administration_area_per_person_in : Real default := 12.0;
        in attribute control_area_per_person_in : Real default := 15.0;
        in attribute security_area_per_person_in : Real default := 12.0;
        in attribute occupancy_circulation_factor_in : Real default := 1.3;
        in attribute occupancy_height_in : Real default := 4.0;
        in attribute heat_rejection_length_in : Real default := 100.0;
        in attribute heat_rejection_width_in : Real default := 60.0;
        in attribute turbine_length_in : Real default := 60.0;
        in attribute turbine_width_in : Real default := 20.0;
        in attribute turbine_height_in : Real default := 15.0;
        in attribute cryo_coldbox_length_in : Real default := 20.0;
        in attribute cryo_coldbox_width_in : Real default := 12.0;
        in attribute cryo_coldbox_height_in : Real default := 10.0;
        in attribute cryo_compressors_length_in : Real default := 30.0;
        in attribute cryo_compressors_width_in : Real default := 12.0;
        in attribute cryo_compressors_height_in : Real default := 8.0;
        in attribute fuel_length_in : Real default := 30.0;
        in attribute fuel_width_in : Real default := 20.0;
        in attribute fuel_height_in : Real default := 8.0;
        in attribute reactor_aux_length_in : Real default := 30.0;
        in attribute reactor_aux_width_in : Real default := 20.0;
        in attribute reactor_aux_height_in : Real default := 10.0;
        in attribute power_supply_length_in : Real default := 20.0;
        in attribute power_supply_width_in : Real default := 10.0;
        in attribute power_supply_height_in : Real default := 8.0;
        in attribute onsite_ac_length_in : Real default := 16.0;
        in attribute onsite_ac_width_in : Real default := 8.0;
        in attribute onsite_ac_height_in : Real default := 6.0;
        in attribute service_water_length_in : Real default := 20.0;
        in attribute service_water_width_in : Real default := 15.0;
        in attribute service_water_height_in : Real default := 8.0;
        in attribute conventional_shop_length_in : Real default := 20.0;
        in attribute conventional_shop_width_in : Real default := 15.0;
        in attribute conventional_shop_height_in : Real default := 8.0;
        in attribute site_services_length_in : Real default := 20.0;
        in attribute site_services_width_in : Real default := 10.0;
        in attribute site_services_height_in : Real default := 6.0;
        in attribute n_mod_in : Real default := 0.0;
        in attribute major_radius_in : Real default := 0.0;
        in attribute minor_outer_radius_in : Real default := 0.0;
        in attribute blanket_volume_in : Real default := 0.0;
        in attribute calendar_q_in : Real default := 0.0;
        in attribute calendar_fluence_in : Real default := 0.0;
        in attribute calendar_years_in : Real default := 0.0;
        in attribute calendar_outage_in : Real default := 0.0;
        in attribute calendar_unplanned_in : Real default := 0.0;
        in attribute calendar_mode_in : Real default := 0.0;
        in attribute calendar_life_in : Real default := 0.0;
        in attribute calendar_count_in : Real default := 0.0;
        in attribute calendar_availability_in : Real default := 0.0;
        in attribute cooling_circuits_in : Real default := 0.0;
        in attribute cooling_helium_count_in : Real default := 0.0;
        in attribute cooling_salt_count_in : Real default := 0.0;
        in attribute cooling_bundle_count_in : Real default := 0.0;
        in attribute cooling_machine_life_in : Real default := 0.0;
        in attribute cooling_bundle_life_in : Real default := 0.0;
        in attribute hx_shell_bore_in : Real default := 0.0;
        in attribute hx_shell_wall_in : Real default := 0.0;
        in attribute hx_shell_length_in : Real default := 0.0;
        in attribute hx_tube_length_in : Real default := 0.0;
        // WI-076 selected civil design; metres unless package count. Dormant zeros are not active defaults.
        in attribute selected_reactor_hall_length_in : Real default := 0.0;
        in attribute selected_reactor_hall_width_in : Real default := 0.0;
        in attribute selected_reactor_hall_height_in : Real default := 0.0;
        in attribute selected_sector_wing_east_length_in : Real default := 0.0;
        in attribute selected_sector_wing_east_width_in : Real default := 0.0;
        in attribute selected_sector_wing_east_height_in : Real default := 0.0;
        in attribute selected_sector_wing_north_length_in : Real default := 0.0;
        in attribute selected_sector_wing_north_width_in : Real default := 0.0;
        in attribute selected_sector_wing_north_height_in : Real default := 0.0;
        in attribute selected_sector_wing_west_length_in : Real default := 0.0;
        in attribute selected_sector_wing_west_width_in : Real default := 0.0;
        in attribute selected_sector_wing_west_height_in : Real default := 0.0;
        in attribute selected_sector_wing_south_length_in : Real default := 0.0;
        in attribute selected_sector_wing_south_width_in : Real default := 0.0;
        in attribute selected_sector_wing_south_height_in : Real default := 0.0;
        in attribute selected_sector_link_east_length_in : Real default := 0.0;
        in attribute selected_sector_link_east_width_in : Real default := 0.0;
        in attribute selected_sector_link_east_height_in : Real default := 0.0;
        in attribute selected_sector_link_north_length_in : Real default := 0.0;
        in attribute selected_sector_link_north_width_in : Real default := 0.0;
        in attribute selected_sector_link_north_height_in : Real default := 0.0;
        in attribute selected_sector_link_west_length_in : Real default := 0.0;
        in attribute selected_sector_link_west_width_in : Real default := 0.0;
        in attribute selected_sector_link_west_height_in : Real default := 0.0;
        in attribute selected_sector_link_south_length_in : Real default := 0.0;
        in attribute selected_sector_link_south_width_in : Real default := 0.0;
        in attribute selected_sector_link_south_height_in : Real default := 0.0;
        in attribute selected_cooling_hall_length_in : Real default := 0.0;
        in attribute selected_cooling_hall_width_in : Real default := 0.0;
        in attribute selected_cooling_hall_height_in : Real default := 0.0;
        in attribute selected_cooling_annex_length_in : Real default := 0.0;
        in attribute selected_cooling_annex_width_in : Real default := 0.0;
        in attribute selected_cooling_annex_height_in : Real default := 0.0;
        in attribute selected_cooling_link_length_in : Real default := 0.0;
        in attribute selected_cooling_link_width_in : Real default := 0.0;
        in attribute selected_cooling_link_height_in : Real default := 0.0;
        in attribute selected_turbine_hall_length_in : Real default := 0.0;
        in attribute selected_turbine_hall_width_in : Real default := 0.0;
        in attribute selected_turbine_hall_height_in : Real default := 0.0;
        in attribute selected_cryo_coldbox_length_in : Real default := 0.0;
        in attribute selected_cryo_coldbox_width_in : Real default := 0.0;
        in attribute selected_cryo_coldbox_height_in : Real default := 0.0;
        in attribute selected_cryo_compressors_length_in : Real default := 0.0;
        in attribute selected_cryo_compressors_width_in : Real default := 0.0;
        in attribute selected_cryo_compressors_height_in : Real default := 0.0;
        in attribute selected_fuel_building_length_in : Real default := 0.0;
        in attribute selected_fuel_building_width_in : Real default := 0.0;
        in attribute selected_fuel_building_height_in : Real default := 0.0;
        in attribute selected_reactor_auxiliaries_length_in : Real default := 0.0;
        in attribute selected_reactor_auxiliaries_width_in : Real default := 0.0;
        in attribute selected_reactor_auxiliaries_height_in : Real default := 0.0;
        in attribute selected_power_supply_building_length_in : Real default := 0.0;
        in attribute selected_power_supply_building_width_in : Real default := 0.0;
        in attribute selected_power_supply_building_height_in : Real default := 0.0;
        in attribute selected_electrical_building_length_in : Real default := 0.0;
        in attribute selected_electrical_building_width_in : Real default := 0.0;
        in attribute selected_electrical_building_height_in : Real default := 0.0;
        in attribute selected_service_water_building_length_in : Real default := 0.0;
        in attribute selected_service_water_building_width_in : Real default := 0.0;
        in attribute selected_service_water_building_height_in : Real default := 0.0;
        in attribute selected_maintenance_shop_length_in : Real default := 0.0;
        in attribute selected_maintenance_shop_width_in : Real default := 0.0;
        in attribute selected_maintenance_shop_height_in : Real default := 0.0;
        in attribute selected_site_services_building_length_in : Real default := 0.0;
        in attribute selected_site_services_building_width_in : Real default := 0.0;
        in attribute selected_site_services_building_height_in : Real default := 0.0;
        in attribute selected_administration_length_in : Real default := 0.0;
        in attribute selected_administration_width_in : Real default := 0.0;
        in attribute selected_administration_height_in : Real default := 0.0;
        in attribute selected_control_length_in : Real default := 0.0;
        in attribute selected_control_width_in : Real default := 0.0;
        in attribute selected_control_height_in : Real default := 0.0;
        in attribute selected_security_length_in : Real default := 0.0;
        in attribute selected_security_width_in : Real default := 0.0;
        in attribute selected_security_height_in : Real default := 0.0;
        in attribute selected_cooling_helium_store_width_in : Real default := 0.0;
        in attribute selected_cooling_salt_store_width_in : Real default := 0.0;
        in attribute selected_cooling_bundle_store_width_in : Real default := 0.0;
        in attribute selected_cooling_annex_north_depth_in : Real default := 0.0;
        in attribute selected_blanket_packages_per_sector_in : Real default := 0.0;
        in attribute selected_parcel_x_min_in : Real default := 0.0;
        in attribute selected_parcel_y_min_in : Real default := 0.0;
        in attribute selected_parcel_length_in : Real default := 0.0;
        in attribute selected_parcel_width_in : Real default := 0.0;
        out attribute active : Real;
        out attribute cost_mode : Real;
        out attribute geometry_fit_margin_m : Real;
        out attribute occupancy_area_margin_m2 : Real;
        out attribute parcel_fit_margin_m : Real;
        out attribute blanket_packages_required_per_sector : Real;
        out attribute required_parcel_x_min : Real;
        out attribute required_parcel_y_min : Real;
        out attribute required_parcel_x_max : Real;
        out attribute required_parcel_y_max : Real;
        out attribute reactor_hall_required_length : Real;
        out attribute reactor_hall_required_width : Real;
        out attribute reactor_hall_required_height : Real;
        out attribute sector_wing_east_required_length : Real;
        out attribute sector_wing_east_required_width : Real;
        out attribute sector_wing_east_required_height : Real;
        out attribute sector_wing_north_required_length : Real;
        out attribute sector_wing_north_required_width : Real;
        out attribute sector_wing_north_required_height : Real;
        out attribute sector_wing_west_required_length : Real;
        out attribute sector_wing_west_required_width : Real;
        out attribute sector_wing_west_required_height : Real;
        out attribute sector_wing_south_required_length : Real;
        out attribute sector_wing_south_required_width : Real;
        out attribute sector_wing_south_required_height : Real;
        out attribute sector_link_east_required_length : Real;
        out attribute sector_link_east_required_width : Real;
        out attribute sector_link_east_required_height : Real;
        out attribute sector_link_north_required_length : Real;
        out attribute sector_link_north_required_width : Real;
        out attribute sector_link_north_required_height : Real;
        out attribute sector_link_west_required_length : Real;
        out attribute sector_link_west_required_width : Real;
        out attribute sector_link_west_required_height : Real;
        out attribute sector_link_south_required_length : Real;
        out attribute sector_link_south_required_width : Real;
        out attribute sector_link_south_required_height : Real;
        out attribute cooling_hall_required_length : Real;
        out attribute cooling_hall_required_width : Real;
        out attribute cooling_hall_required_height : Real;
        out attribute cooling_annex_required_length : Real;
        out attribute cooling_annex_required_width : Real;
        out attribute cooling_annex_required_height : Real;
        out attribute cooling_link_required_length : Real;
        out attribute cooling_link_required_width : Real;
        out attribute cooling_link_required_height : Real;
        out attribute turbine_hall_required_length : Real;
        out attribute turbine_hall_required_width : Real;
        out attribute turbine_hall_required_height : Real;
        out attribute cryo_coldbox_required_length : Real;
        out attribute cryo_coldbox_required_width : Real;
        out attribute cryo_coldbox_required_height : Real;
        out attribute cryo_compressors_required_length : Real;
        out attribute cryo_compressors_required_width : Real;
        out attribute cryo_compressors_required_height : Real;
        out attribute fuel_building_required_length : Real;
        out attribute fuel_building_required_width : Real;
        out attribute fuel_building_required_height : Real;
        out attribute reactor_auxiliaries_required_length : Real;
        out attribute reactor_auxiliaries_required_width : Real;
        out attribute reactor_auxiliaries_required_height : Real;
        out attribute power_supply_building_required_length : Real;
        out attribute power_supply_building_required_width : Real;
        out attribute power_supply_building_required_height : Real;
        out attribute electrical_building_required_length : Real;
        out attribute electrical_building_required_width : Real;
        out attribute electrical_building_required_height : Real;
        out attribute service_water_building_required_length : Real;
        out attribute service_water_building_required_width : Real;
        out attribute service_water_building_required_height : Real;
        out attribute maintenance_shop_required_length : Real;
        out attribute maintenance_shop_required_width : Real;
        out attribute maintenance_shop_required_height : Real;
        out attribute site_services_building_required_length : Real;
        out attribute site_services_building_required_width : Real;
        out attribute site_services_building_required_height : Real;
        out attribute administration_required_area : Real;
        out attribute administration_required_height : Real;
        out attribute control_required_area : Real;
        out attribute control_required_height : Real;
        out attribute security_required_area : Real;
        out attribute security_required_height : Real;

        out attribute sector_length : Real;
        out attribute sector_width : Real;
        out attribute sector_height : Real;
        out attribute parcel_area : Real;
        out attribute controlled_air_volume : Real;
        out attribute total_clear_area : Real;
        out attribute total_gross_area : Real;
        out attribute total_air_volume : Real;
        out attribute blanket_packages_per_sector : Real;
        out attribute packages_per_sector : Real;
        out attribute material_capacity_volume : Real;
        out attribute unused_material_capacity : Real;
        out attribute initial_clean_required : Real;
        out attribute dirty_buffer_required : Real;
        out attribute dirty_store_required : Real;
        out attribute initial_ready_margin_days : Real;
        out attribute replacement_ready_margin_days : Real;
        out attribute outage_required_days : Real;
        out attribute outage_allowed_days : Real;
        out attribute outage_margin_days : Real;
        out attribute calendar_event_count : Real;
        out attribute calendar_first_event_year : Real;
        out attribute calendar_last_event_year : Real;
        out attribute cooling_clean_helium_required : Real;
        out attribute cooling_clean_salt_required : Real;
        out attribute cooling_clean_bundle_required : Real;
        out attribute cooling_dirty_helium_required : Real;
        out attribute cooling_dirty_salt_required : Real;
        out attribute cooling_dirty_bundle_required : Real;
        out attribute cooling_helium_queue_peak : Real;
        out attribute cooling_salt_queue_peak : Real;
        out attribute cooling_bundle_queue_peak : Real;
        out attribute cooling_initial_ready_margin_days : Real;
        out attribute cooling_replacement_ready_margin_days : Real;
        out attribute cooling_jobs_after_shutdown : Real;
        out attribute cooling_last_release_year : Real;
        out attribute cooling_carrier_moves : Real;
        out attribute clean_positions_allocated : Real;
        out attribute dirty_buffer_positions_allocated : Real;
        out attribute dirty_store_positions_allocated : Real;
        out attribute cooling_clean_helium_allocated : Real;
        out attribute cooling_clean_salt_allocated : Real;
        out attribute cooling_clean_bundle_allocated : Real;
        out attribute cooling_dirty_helium_allocated : Real;
        out attribute cooling_dirty_salt_allocated : Real;
        out attribute cooling_dirty_bundle_allocated : Real;
        out attribute initial_margin_days : Real;
        out attribute readiness_margin_days : Real;
        out attribute capacity_margin_units : Real;
        out attribute route_margin_m : Real;
        out attribute exterior_envelope_qualified : Real;
        out attribute sector_load_qualified : Real;
        out attribute contamination_procedure_qualified : Real;
        out attribute cooling_outage_basis_resolved : Real;
        out attribute provisional_room_count : Real;
        out attribute reactor_hall_clear_length : Real;
        out attribute reactor_hall_clear_width : Real;
        out attribute reactor_hall_clear_height : Real;
        out attribute reactor_hall_clear_area : Real;
        out attribute reactor_hall_gross_area : Real;
        out attribute reactor_hall_air_volume : Real;
        out attribute reactor_hall_sub_concrete : Real;
        out attribute reactor_hall_super_concrete : Real;
        out attribute reactor_hall_sub_formwork : Real;
        out attribute reactor_hall_super_formwork : Real;
        out attribute reactor_hall_sub_rebar : Real;
        out attribute reactor_hall_super_rebar : Real;
        out attribute sector_wing_east_clear_length : Real;
        out attribute sector_wing_east_clear_width : Real;
        out attribute sector_wing_east_clear_height : Real;
        out attribute sector_wing_east_clear_area : Real;
        out attribute sector_wing_east_gross_area : Real;
        out attribute sector_wing_east_air_volume : Real;
        out attribute sector_wing_east_sub_concrete : Real;
        out attribute sector_wing_east_super_concrete : Real;
        out attribute sector_wing_east_sub_formwork : Real;
        out attribute sector_wing_east_super_formwork : Real;
        out attribute sector_wing_east_sub_rebar : Real;
        out attribute sector_wing_east_super_rebar : Real;
        out attribute sector_wing_north_clear_length : Real;
        out attribute sector_wing_north_clear_width : Real;
        out attribute sector_wing_north_clear_height : Real;
        out attribute sector_wing_north_clear_area : Real;
        out attribute sector_wing_north_gross_area : Real;
        out attribute sector_wing_north_air_volume : Real;
        out attribute sector_wing_north_sub_concrete : Real;
        out attribute sector_wing_north_super_concrete : Real;
        out attribute sector_wing_north_sub_formwork : Real;
        out attribute sector_wing_north_super_formwork : Real;
        out attribute sector_wing_north_sub_rebar : Real;
        out attribute sector_wing_north_super_rebar : Real;
        out attribute sector_wing_west_clear_length : Real;
        out attribute sector_wing_west_clear_width : Real;
        out attribute sector_wing_west_clear_height : Real;
        out attribute sector_wing_west_clear_area : Real;
        out attribute sector_wing_west_gross_area : Real;
        out attribute sector_wing_west_air_volume : Real;
        out attribute sector_wing_west_sub_concrete : Real;
        out attribute sector_wing_west_super_concrete : Real;
        out attribute sector_wing_west_sub_formwork : Real;
        out attribute sector_wing_west_super_formwork : Real;
        out attribute sector_wing_west_sub_rebar : Real;
        out attribute sector_wing_west_super_rebar : Real;
        out attribute sector_wing_south_clear_length : Real;
        out attribute sector_wing_south_clear_width : Real;
        out attribute sector_wing_south_clear_height : Real;
        out attribute sector_wing_south_clear_area : Real;
        out attribute sector_wing_south_gross_area : Real;
        out attribute sector_wing_south_air_volume : Real;
        out attribute sector_wing_south_sub_concrete : Real;
        out attribute sector_wing_south_super_concrete : Real;
        out attribute sector_wing_south_sub_formwork : Real;
        out attribute sector_wing_south_super_formwork : Real;
        out attribute sector_wing_south_sub_rebar : Real;
        out attribute sector_wing_south_super_rebar : Real;
        out attribute sector_link_east_clear_length : Real;
        out attribute sector_link_east_clear_width : Real;
        out attribute sector_link_east_clear_height : Real;
        out attribute sector_link_east_clear_area : Real;
        out attribute sector_link_east_gross_area : Real;
        out attribute sector_link_east_air_volume : Real;
        out attribute sector_link_east_sub_concrete : Real;
        out attribute sector_link_east_super_concrete : Real;
        out attribute sector_link_east_sub_formwork : Real;
        out attribute sector_link_east_super_formwork : Real;
        out attribute sector_link_east_sub_rebar : Real;
        out attribute sector_link_east_super_rebar : Real;
        out attribute sector_link_north_clear_length : Real;
        out attribute sector_link_north_clear_width : Real;
        out attribute sector_link_north_clear_height : Real;
        out attribute sector_link_north_clear_area : Real;
        out attribute sector_link_north_gross_area : Real;
        out attribute sector_link_north_air_volume : Real;
        out attribute sector_link_north_sub_concrete : Real;
        out attribute sector_link_north_super_concrete : Real;
        out attribute sector_link_north_sub_formwork : Real;
        out attribute sector_link_north_super_formwork : Real;
        out attribute sector_link_north_sub_rebar : Real;
        out attribute sector_link_north_super_rebar : Real;
        out attribute sector_link_west_clear_length : Real;
        out attribute sector_link_west_clear_width : Real;
        out attribute sector_link_west_clear_height : Real;
        out attribute sector_link_west_clear_area : Real;
        out attribute sector_link_west_gross_area : Real;
        out attribute sector_link_west_air_volume : Real;
        out attribute sector_link_west_sub_concrete : Real;
        out attribute sector_link_west_super_concrete : Real;
        out attribute sector_link_west_sub_formwork : Real;
        out attribute sector_link_west_super_formwork : Real;
        out attribute sector_link_west_sub_rebar : Real;
        out attribute sector_link_west_super_rebar : Real;
        out attribute sector_link_south_clear_length : Real;
        out attribute sector_link_south_clear_width : Real;
        out attribute sector_link_south_clear_height : Real;
        out attribute sector_link_south_clear_area : Real;
        out attribute sector_link_south_gross_area : Real;
        out attribute sector_link_south_air_volume : Real;
        out attribute sector_link_south_sub_concrete : Real;
        out attribute sector_link_south_super_concrete : Real;
        out attribute sector_link_south_sub_formwork : Real;
        out attribute sector_link_south_super_formwork : Real;
        out attribute sector_link_south_sub_rebar : Real;
        out attribute sector_link_south_super_rebar : Real;
        out attribute cooling_hall_clear_length : Real;
        out attribute cooling_hall_clear_width : Real;
        out attribute cooling_hall_clear_height : Real;
        out attribute cooling_hall_clear_area : Real;
        out attribute cooling_hall_gross_area : Real;
        out attribute cooling_hall_air_volume : Real;
        out attribute cooling_hall_sub_concrete : Real;
        out attribute cooling_hall_super_concrete : Real;
        out attribute cooling_hall_sub_formwork : Real;
        out attribute cooling_hall_super_formwork : Real;
        out attribute cooling_hall_sub_rebar : Real;
        out attribute cooling_hall_super_rebar : Real;
        out attribute cooling_annex_clear_length : Real;
        out attribute cooling_annex_clear_width : Real;
        out attribute cooling_annex_clear_height : Real;
        out attribute cooling_annex_clear_area : Real;
        out attribute cooling_annex_gross_area : Real;
        out attribute cooling_annex_air_volume : Real;
        out attribute cooling_annex_sub_concrete : Real;
        out attribute cooling_annex_super_concrete : Real;
        out attribute cooling_annex_sub_formwork : Real;
        out attribute cooling_annex_super_formwork : Real;
        out attribute cooling_annex_sub_rebar : Real;
        out attribute cooling_annex_super_rebar : Real;
        out attribute cooling_link_clear_length : Real;
        out attribute cooling_link_clear_width : Real;
        out attribute cooling_link_clear_height : Real;
        out attribute cooling_link_clear_area : Real;
        out attribute cooling_link_gross_area : Real;
        out attribute cooling_link_air_volume : Real;
        out attribute cooling_link_sub_concrete : Real;
        out attribute cooling_link_super_concrete : Real;
        out attribute cooling_link_sub_formwork : Real;
        out attribute cooling_link_super_formwork : Real;
        out attribute cooling_link_sub_rebar : Real;
        out attribute cooling_link_super_rebar : Real;
        out attribute turbine_hall_clear_length : Real;
        out attribute turbine_hall_clear_width : Real;
        out attribute turbine_hall_clear_height : Real;
        out attribute turbine_hall_clear_area : Real;
        out attribute turbine_hall_gross_area : Real;
        out attribute turbine_hall_air_volume : Real;
        out attribute turbine_hall_sub_concrete : Real;
        out attribute turbine_hall_super_concrete : Real;
        out attribute turbine_hall_sub_formwork : Real;
        out attribute turbine_hall_super_formwork : Real;
        out attribute turbine_hall_sub_rebar : Real;
        out attribute turbine_hall_super_rebar : Real;
        out attribute cryo_coldbox_clear_length : Real;
        out attribute cryo_coldbox_clear_width : Real;
        out attribute cryo_coldbox_clear_height : Real;
        out attribute cryo_coldbox_clear_area : Real;
        out attribute cryo_coldbox_gross_area : Real;
        out attribute cryo_coldbox_air_volume : Real;
        out attribute cryo_coldbox_sub_concrete : Real;
        out attribute cryo_coldbox_super_concrete : Real;
        out attribute cryo_coldbox_sub_formwork : Real;
        out attribute cryo_coldbox_super_formwork : Real;
        out attribute cryo_coldbox_sub_rebar : Real;
        out attribute cryo_coldbox_super_rebar : Real;
        out attribute cryo_compressors_clear_length : Real;
        out attribute cryo_compressors_clear_width : Real;
        out attribute cryo_compressors_clear_height : Real;
        out attribute cryo_compressors_clear_area : Real;
        out attribute cryo_compressors_gross_area : Real;
        out attribute cryo_compressors_air_volume : Real;
        out attribute cryo_compressors_sub_concrete : Real;
        out attribute cryo_compressors_super_concrete : Real;
        out attribute cryo_compressors_sub_formwork : Real;
        out attribute cryo_compressors_super_formwork : Real;
        out attribute cryo_compressors_sub_rebar : Real;
        out attribute cryo_compressors_super_rebar : Real;
        out attribute fuel_building_clear_length : Real;
        out attribute fuel_building_clear_width : Real;
        out attribute fuel_building_clear_height : Real;
        out attribute fuel_building_clear_area : Real;
        out attribute fuel_building_gross_area : Real;
        out attribute fuel_building_air_volume : Real;
        out attribute fuel_building_sub_concrete : Real;
        out attribute fuel_building_super_concrete : Real;
        out attribute fuel_building_sub_formwork : Real;
        out attribute fuel_building_super_formwork : Real;
        out attribute fuel_building_sub_rebar : Real;
        out attribute fuel_building_super_rebar : Real;
        out attribute reactor_auxiliaries_clear_length : Real;
        out attribute reactor_auxiliaries_clear_width : Real;
        out attribute reactor_auxiliaries_clear_height : Real;
        out attribute reactor_auxiliaries_clear_area : Real;
        out attribute reactor_auxiliaries_gross_area : Real;
        out attribute reactor_auxiliaries_air_volume : Real;
        out attribute reactor_auxiliaries_sub_concrete : Real;
        out attribute reactor_auxiliaries_super_concrete : Real;
        out attribute reactor_auxiliaries_sub_formwork : Real;
        out attribute reactor_auxiliaries_super_formwork : Real;
        out attribute reactor_auxiliaries_sub_rebar : Real;
        out attribute reactor_auxiliaries_super_rebar : Real;
        out attribute power_supply_building_clear_length : Real;
        out attribute power_supply_building_clear_width : Real;
        out attribute power_supply_building_clear_height : Real;
        out attribute power_supply_building_clear_area : Real;
        out attribute power_supply_building_gross_area : Real;
        out attribute power_supply_building_air_volume : Real;
        out attribute power_supply_building_sub_concrete : Real;
        out attribute power_supply_building_super_concrete : Real;
        out attribute power_supply_building_sub_formwork : Real;
        out attribute power_supply_building_super_formwork : Real;
        out attribute power_supply_building_sub_rebar : Real;
        out attribute power_supply_building_super_rebar : Real;
        out attribute electrical_building_clear_length : Real;
        out attribute electrical_building_clear_width : Real;
        out attribute electrical_building_clear_height : Real;
        out attribute electrical_building_clear_area : Real;
        out attribute electrical_building_gross_area : Real;
        out attribute electrical_building_air_volume : Real;
        out attribute electrical_building_sub_concrete : Real;
        out attribute electrical_building_super_concrete : Real;
        out attribute electrical_building_sub_formwork : Real;
        out attribute electrical_building_super_formwork : Real;
        out attribute electrical_building_sub_rebar : Real;
        out attribute electrical_building_super_rebar : Real;
        out attribute service_water_building_clear_length : Real;
        out attribute service_water_building_clear_width : Real;
        out attribute service_water_building_clear_height : Real;
        out attribute service_water_building_clear_area : Real;
        out attribute service_water_building_gross_area : Real;
        out attribute service_water_building_air_volume : Real;
        out attribute service_water_building_sub_concrete : Real;
        out attribute service_water_building_super_concrete : Real;
        out attribute service_water_building_sub_formwork : Real;
        out attribute service_water_building_super_formwork : Real;
        out attribute service_water_building_sub_rebar : Real;
        out attribute service_water_building_super_rebar : Real;
        out attribute maintenance_shop_clear_length : Real;
        out attribute maintenance_shop_clear_width : Real;
        out attribute maintenance_shop_clear_height : Real;
        out attribute maintenance_shop_clear_area : Real;
        out attribute maintenance_shop_gross_area : Real;
        out attribute maintenance_shop_air_volume : Real;
        out attribute maintenance_shop_sub_concrete : Real;
        out attribute maintenance_shop_super_concrete : Real;
        out attribute maintenance_shop_sub_formwork : Real;
        out attribute maintenance_shop_super_formwork : Real;
        out attribute maintenance_shop_sub_rebar : Real;
        out attribute maintenance_shop_super_rebar : Real;
        out attribute site_services_building_clear_length : Real;
        out attribute site_services_building_clear_width : Real;
        out attribute site_services_building_clear_height : Real;
        out attribute site_services_building_clear_area : Real;
        out attribute site_services_building_gross_area : Real;
        out attribute site_services_building_air_volume : Real;
        out attribute site_services_building_sub_concrete : Real;
        out attribute site_services_building_super_concrete : Real;
        out attribute site_services_building_sub_formwork : Real;
        out attribute site_services_building_super_formwork : Real;
        out attribute site_services_building_sub_rebar : Real;
        out attribute site_services_building_super_rebar : Real;
        out attribute administration_clear_length : Real;
        out attribute administration_clear_width : Real;
        out attribute administration_clear_height : Real;
        out attribute administration_clear_area : Real;
        out attribute administration_gross_area : Real;
        out attribute administration_air_volume : Real;
        out attribute administration_sub_concrete : Real;
        out attribute administration_super_concrete : Real;
        out attribute administration_sub_formwork : Real;
        out attribute administration_super_formwork : Real;
        out attribute administration_sub_rebar : Real;
        out attribute administration_super_rebar : Real;
        out attribute control_clear_length : Real;
        out attribute control_clear_width : Real;
        out attribute control_clear_height : Real;
        out attribute control_clear_area : Real;
        out attribute control_gross_area : Real;
        out attribute control_air_volume : Real;
        out attribute control_sub_concrete : Real;
        out attribute control_super_concrete : Real;
        out attribute control_sub_formwork : Real;
        out attribute control_super_formwork : Real;
        out attribute control_sub_rebar : Real;
        out attribute control_super_rebar : Real;
        out attribute security_clear_length : Real;
        out attribute security_clear_width : Real;
        out attribute security_clear_height : Real;
        out attribute security_clear_area : Real;
        out attribute security_gross_area : Real;
        out attribute security_air_volume : Real;
        out attribute security_sub_concrete : Real;
        out attribute security_super_concrete : Real;
        out attribute security_sub_formwork : Real;
        out attribute security_super_formwork : Real;
        out attribute security_sub_rebar : Real;
        out attribute security_super_rebar : Real;
    }
    calc def 'Facility Civil Cost' {
        doc /* Source: work/active/WI-068_layout-based-facilities/design.md; layout-capacity-design.md; evidence/facility-contract.md. Ref: released geometry, capacity, exact civil takeoff and account boundary. Basis: conditional conceptual scenario; unqualified shielding/loading/transport and explicit provisional equipment envelopes. Six installed-direct commodity products, original2018 and CPI-normalized2025 purchasing power. Disabled returns zero; no repeated installation. */
        in attribute enabled_in : Boolean;
        in attribute sub_concrete_in : Real;
        in attribute super_concrete_in : Real;
        in attribute sub_formwork_in : Real;
        in attribute super_formwork_in : Real;
        in attribute sub_rebar_in : Real;
        in attribute super_rebar_in : Real;
        in attribute sub_concrete_rate_in : Real;
        in attribute sub_formwork_rate_in : Real;
        in attribute sub_rebar_rate_in : Real;
        in attribute super_concrete_rate_in : Real;
        in attribute super_formwork_rate_in : Real;
        in attribute super_rebar_rate_in : Real;
        in attribute civil_cpi_ratio_in : Real;
        in attribute civil_rate_multiplier_in : Real;
        in attribute tonne_interpretation_kg_in : Real;
        out attribute sub_cost_2018 : Real;
        out attribute super_cost_2018 : Real;
        out attribute cost_2018 : Real;
        out attribute cost_2025 : Real;
    }
    calc def 'Facility Shipping Scope' {
        doc /* Source: work/active/WI-068_layout-based-facilities/design.md; layout-capacity-design.md; evidence/facility-contract.md. Ref: released geometry, capacity, exact civil takeoff and account boundary. Basis: conditional conceptual scenario; unqualified shielding/loading/transport and explicit provisional equipment envelopes. Reject negative/nonfinite exclusions or sum exceedingCAS20, never clamp. */
        in attribute cas20_in : Real;
        in attribute cooling_exclusion_in : Real;
        in attribute facility_exclusion_in : Real;
        in attribute fuel_installation_in : Real default 0.0;
        in attribute contingency_in : Real default 0.0;
        out attribute fuel_installation_exclusion : Real;
        out attribute cooling_exclusion : Real;
        out attribute facility_exclusion : Real;
        out attribute remaining_shipping_base : Real;
    }
    calc def 'Facility Ventilation Cost' {
        doc /* Source: work/active/WI-068_layout-based-facilities/design.md; layout-capacity-design.md; evidence/facility-contract.md. Ref: released geometry, capacity, exact civil takeoff and account boundary. Basis: conditional conceptual scenario; unqualified shielding/loading/transport and explicit provisional equipment envelopes. Historical PROCESS1990 empirical nuclear-ventilation relation; does not qualify airflow. */
        in attribute served_volume_in : Real;
        in attribute coefficient_in : Real;
        in attribute exponent_in : Real;
        in attribute cpi_ratio_in : Real;
        out attribute cost_1990 : Real = coefficient_in * served_volume_in ** exponent_in;
        out attribute cost_2025 : Real = cost_1990 * cpi_ratio_in;
    }
    constraint def 'Facility Nonnegative Margin' {
        doc /* Source: work/active/WI-068_layout-based-facilities/design.md; layout-capacity-design.md; evidence/facility-contract.md. Ref: released geometry, capacity, exact civil takeoff and account boundary. Basis: conditional conceptual scenario; unqualified shielding/loading/transport and explicit provisional equipment envelopes. Executable compatibility check only; qualification remains disclosed separately. */
        in margin_in : Real;
        margin_in >= 0.0
    }

    calc def 'Facility Civil Rollup' {
        doc /* **Source**: work/active/WI-068_layout-based-facilities/design.md. **Ref**: account replacement map and component-owned aggregation. **Basis**: Sum the actual25 civil component costs once. */
        in attribute reactor_hall_in : Real;
        in attribute sector_wing_east_in : Real;
        in attribute sector_wing_north_in : Real;
        in attribute sector_wing_west_in : Real;
        in attribute sector_wing_south_in : Real;
        in attribute sector_link_east_in : Real;
        in attribute sector_link_north_in : Real;
        in attribute sector_link_west_in : Real;
        in attribute sector_link_south_in : Real;
        in attribute cooling_hall_in : Real;
        in attribute cooling_annex_in : Real;
        in attribute cooling_link_in : Real;
        in attribute turbine_hall_in : Real;
        in attribute cryo_coldbox_in : Real;
        in attribute cryo_compressors_in : Real;
        in attribute fuel_building_in : Real;
        in attribute reactor_auxiliaries_in : Real;
        in attribute power_supply_building_in : Real;
        in attribute electrical_building_in : Real;
        in attribute service_water_building_in : Real;
        in attribute maintenance_shop_in : Real;
        in attribute site_services_building_in : Real;
        in attribute administration_in : Real;
        in attribute control_in : Real;
        in attribute security_in : Real;
        out attribute civil_capital : Real = reactor_hall_in + sector_wing_east_in + sector_wing_north_in + sector_wing_west_in + sector_wing_south_in + sector_link_east_in + sector_link_north_in + sector_link_west_in + sector_link_south_in + cooling_hall_in + cooling_annex_in + cooling_link_in + turbine_hall_in + cryo_coldbox_in + cryo_compressors_in + fuel_building_in + reactor_auxiliaries_in + power_supply_building_in + electrical_building_in + service_water_building_in + maintenance_shop_in + site_services_building_in + administration_in + control_in + security_in;
    }
    calc def 'Facility Account Selection' {
        doc /* **Source**: work/active/WI-068_layout-based-facilities/design.md. **Ref**: account replacement map and component-owned aggregation. **Basis**: Select the complete priced facility account or the preserved grouped legacy account; layout validates the binary mode. */
        in attribute civil_in : Real;
        in attribute ventilation_in : Real;
        in attribute site_in : Real;
        in attribute legacy_in : Real;
        in attribute mode_in : Real;
        out attribute installed_facility_capital : Real = civil_in + ventilation_in;
        out attribute layout_buildings_capital : Real = installed_facility_capital + site_in;
        out attribute cost : Real = (1.0 - mode_in) * legacy_in + mode_in * layout_buildings_capital;
    }
    calc def 'Facility Land Cost' {
        doc /* **Source**: work/active/WI-068_layout-based-facilities/design.md. **Ref**: account replacement map and component-owned aggregation. **Basis**: Convert the computed parcel area in m^2 to acres at the explicit inherited land rate. */
        in attribute parcel_area_in : Real;
        in attribute rate_per_acre_in : Real;
        out attribute cost : Real = parcel_area_in / 4046.8564224 * rate_per_acre_in;
    }
    calc def 'Facility Site Allowance' {
        doc /* **Source**: work/active/WI-068_layout-based-facilities/design.md. **Ref**: account replacement map and component-owned aggregation. **Basis**: Retain the identified site-improvement allowance once in an active proposed layout; dormant contribution zero. */
        in attribute active_in : Real;
        in attribute amount_in : Real;
        out attribute cost : Real = active_in * amount_in;
    }
    calc def 'Facility Preconstruction Selection' {
        doc /* **Source**: work/active/WI-068_layout-based-facilities/design.md. **Ref**: account replacement map and component-owned aggregation. **Basis**: Replace only land; keep the fixed preconstruction adders and legacy mode. */
        in attribute mode_in : Real;
        in attribute legacy_in : Real;
        in attribute fixed_in : Real;
        in attribute land_in : Real;
        out attribute cost : Real = (1.0 - mode_in) * legacy_in + mode_in * (fixed_in + land_in);
    }
    calc def 'Facility Shipping Amount' {
        doc /* **Source**: work/active/WI-068_layout-based-facilities/design.md. **Ref**: account replacement map and component-owned aggregation. **Basis**: Exclude the entire contingency-loaded installed facility contribution from freight, without altering tax or insurance. */
        in attribute mode_in : Real;
        in attribute contingency_in : Real;
        in attribute installed_in : Real;
        out attribute exclusion : Real = mode_in * (1.0 + contingency_in) * installed_in;
    }
}
