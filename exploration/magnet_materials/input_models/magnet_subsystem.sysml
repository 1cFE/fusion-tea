package magnet_subsystem {
    doc /* Matched-duty magnet subsystem: one supplied Nb3Sn winding and one supplied REBCO winding carrying the same duty in the same envelope (anchor D, EU DEMO TF, primary matched comparison). Defaults are the anchor D reference case at 10 T with policy-generated reference offers on construction P; every value is an overridable input and cases override them through the study route. **Source**: work/active/WI-099_magnet-conductor-alternatives/reference-case.json (generated by make_reference_case.py) **Reference**: work/active/WI-099_magnet-conductor-alternatives/design.md sections 3, 4 and 6; work/orchestration/goals/magnet-material-comparison/evidence/comparison-contract.md (r3). **Basis**: [AGENT] reviewed design; subsystem screening, not a qualified magnet design. **Last Updated**: 2026-09-29 */
    private import ScalarValues::*;
    private import magnet_conductor_alternatives::*;
    part subsystem {
        doc /* Duty, economics, the two material windings and their matched-pair comparison. Consumers bind producer attributes (EXPOSE pattern), never calc internals. **Source**: work/active/WI-099_magnet-conductor-alternatives/reference-case.json **Reference**: design.md section 3 **Basis**: [AGENT] reviewed design **Last Updated**: 2026-09-29 */
        part duty {
            doc /* Anchor duty: excitation varies, geometry does not. turn_current = I_ref*B_peak/B_ref (field proportional to ampere-turns at fixed air-core geometry, contract section 2). **Source**: work/orchestration/goals/magnet-material-comparison/evidence/comparison-contract.md **Reference**: section 2, anchor D **Basis**: [AGENT] matched-duty boundary **Last Updated**: 2026-09-29 */
            attribute coils : Real = 16.0 {
                doc /* **Source**: knowledge/sources/eu_demo_rw_tf_coil_conductor_dematte_bruzzone/raw.pdf **Reference**: p.2 section III (16 TF coils, 142 turns); contract section 2 anchor D **Basis**: directly supported **Last Updated**: 2026-09-29 */
            }
            attribute turns : Real = 142.0 {
                doc /* **Source**: knowledge/sources/eu_demo_rw_tf_coil_conductor_dematte_bruzzone/raw.pdf **Reference**: p.2 section III, 142 turns per coil (14.903 MA per coil) **Basis**: directly supported **Last Updated**: 2026-09-29 */
            }
            attribute turn_length : Real = 55.6 {
                doc /* **Source**: knowledge/sources/eu_demo_rw_tf_coil_conductor_dematte_bruzzone/raw.pdf **Reference**: p.1 (about 1 km layer sections) / 18 turns per layer; contract section 2 anchor D table **Basis**: bounded assumption: 55.6 m; ITER cross-check 50 m; sensitivity 45 and 60 m **Last Updated**: 2026-09-29 */
            }
            attribute available_area : Real = 3751.0985915492956 {
                doc /* **Source**: knowledge/sources/eu_demo_rw_tf_coil_conductor_dematte_bruzzone/raw.pdf **Reference**: winding pack 1296 x 411 mm / 142 turns (Table I, p.2); contract section 2 **Basis**: [AGENT] gross envelope per turn [mm2], every turn sized at peak field (no layer grading) **Last Updated**: 2026-09-29 */
            }
            attribute I_ref : Real = 104950.0 {
                doc /* **Source**: knowledge/sources/eu_demo_rw_tf_coil_conductor_dematte_bruzzone/raw.pdf **Reference**: p.2-3 section III/V, 104.95 kA operating current **Basis**: directly supported; units A (no bracketed tokens: a formula operand doc is read for a unit) **Last Updated**: 2026-09-29 */
            }
            attribute B_ref : Real = 12.04 {
                doc /* **Source**: knowledge/sources/eu_demo_rw_tf_coil_conductor_dematte_bruzzone/raw.pdf **Reference**: p.3 below eq. (1), B_eff = 12.04 T **Basis**: directly supported; units T **Last Updated**: 2026-09-29 */
            }
            attribute B_peak : Real = 10.0 {
                doc /* **Source**: work/orchestration/goals/magnet-material-comparison/evidence/comparison-contract.md **Reference**: section 2 field points (8-13 T matched, 14-20 T REBCO-only extension) **Basis**: AGENT choice: design default 10 T, overridden per case; units T **Last Updated**: 2026-09-29 */
            }
            attribute turn_current : Real = I_ref * B_peak / B_ref;
        }
        part economics {
            doc /* Economic inputs common to both windings. **Source**: work/orchestration/goals/magnet-material-comparison/evidence/comparison-contract.md **Reference**: section 7 **Basis**: [AGENT] single currency USD2021 **Last Updated**: 2026-09-29 */
            attribute crf : Real = 0.08 {
                doc /* **Source**: work/orchestration/goals/magnet-material-comparison/evidence/comparison-contract.md **Reference**: section 7, capital recovery factor 0.08 **Basis**: [AGENT]; sensitivity 0.05 and 0.11 [1/yr] **Last Updated**: 2026-09-29 */
            }
            attribute availability : Real = 0.8 {
                doc /* **Source**: work/orchestration/goals/magnet-material-comparison/evidence/comparison-contract.md **Reference**: section 7, 0.8 availability **Basis**: [AGENT] [1] **Last Updated**: 2026-09-29 */
            }
            attribute electricity_price : Real = 60.0 {
                doc /* **Source**: work/orchestration/goals/magnet-material-comparison/evidence/comparison-contract.md **Reference**: section 7, 60 USD/MWh **Basis**: [AGENT]; sensitivity 30 and 120 [USD2021/MWh] **Last Updated**: 2026-09-29 */
            }
            attribute hours : Real = 8760.0 {
                doc /* **Source**: work/orchestration/goals/magnet-material-comparison/evidence/comparison-contract.md **Reference**: section 7, 8760 h **Basis**: hours per year [h] **Last Updated**: 2026-09-29 */
            }
            attribute usd2015_to_2021 : Real = 1.1434599156118144 {
                doc /* **Source**: knowledge/sources/federal_reserve_bank_of_minneapolis_annual_consumer_price/output.md **Reference**: line 731 (2015, CPI 237.0) and line 773 (2021, CPI 271.0); check-rebco-cryo-cost.md section 7 **Basis**: ratio 271.0/237.0 [1] **Last Updated**: 2026-09-29 */
            }
        }
        part nb3sn {
            doc /* Supplied Nb3Sn strand cable, EU DEMO react-and-wind flat-cable conductor, 4.5 K helium supply, on construction P (common-P reference pairing). Owns its supplied offer (element count, construction areas, temperatures, installed refrigerator rating, prices) and evaluates it; asserts its five constraints. Design defaults are the anchor D reference case at 10 T; all values are overridable case inputs. **Source**: work/active/WI-099_magnet-conductor-alternatives/reference-case.json **Reference**: work/active/WI-099_magnet-conductor-alternatives/design.md sections 3, 4 and 6; work/orchestration/goals/magnet-material-comparison/evidence/comparison-contract.md sections 3-7. **Basis**: [AGENT] reviewed design; MR-7 role record in design section 4. **Last Updated**: 2026-09-29 */
            // Conductor definition and chosen temperatures (design section 6, conductor).
            attribute n_elements : Real = 438.0 {
                doc /* **Source**: work/active/WI-099_magnet-conductor-alternatives/reference-case.json **Reference**: nb3sn.n_elements **Basis**: [AGENT] reference offer: smallest integer strand count meeting the Nb3Sn temperature rule at the reference duty (contract section 5); supplied, never resized [1] **Last Updated**: 2026-09-29 */
            }
            attribute T_supply : Real = 4.5 {
                doc /* **Source**: knowledge/sources/advance_in_the_conceptual_design_of_the_european_demo/raw.pdf **Reference**: PDF p.3: Tcs 6.7 K = 4.5 K inlet + 0.7 K nuclear heat + 1.5 K margin **Basis**: refrigerator supply temperature [K] **Last Updated**: 2026-09-29 */
            }
            attribute nuclear_rise : Real = 0.7 {
                doc /* **Source**: knowledge/sources/advance_in_the_conceptual_design_of_the_european_demo/raw.pdf **Reference**: PDF p.3, 0.7 K for nuclear heat load **Basis**: directly supported [K] **Last Updated**: 2026-09-29 */
            }
            attribute margin_rise : Real = 1.5 {
                doc /* **Source**: knowledge/sources/advance_in_the_conceptual_design_of_the_european_demo/raw.pdf **Reference**: PDF p.3, 1.5 K temperature margin **Basis**: directly supported [K] **Last Updated**: 2026-09-29 */
            }
            attribute fraction_rule : Real = 0.8 {
                doc /* **Source**: work/orchestration/goals/magnet-material-comparison/evidence/comparison-contract.md **Reference**: section 3 fraction rule I <= 0.8 Ic **Basis**: [AGENT] existing model convention (WI-062) [1] **Last Updated**: 2026-09-29 */
            }
            attribute acceptance_rule : Real = 0.0 {
                doc /* **Source**: work/orchestration/goals/magnet-material-comparison/evidence/comparison-contract.md **Reference**: section 3 reference acceptance: Nb3Sn temperature rule **Basis**: sourced rule; 0 = temperature rule **Last Updated**: 2026-09-29 */
            }
            attribute strand_diameter : Real = 0.00082 {
                doc /* **Source**: knowledge/sources/critical_current_scaling_and_the_pivot_point_in_nb3sn/raw.pdf **Reference**: Table 1, PDF p.3: ITER TF strand 0.820 +/- 0.005 mm **Basis**: C1 is per whole 0.82 mm strand (check-nb3sn.md Recheck r3 item 8) [m] **Last Updated**: 2026-09-29 */
            }
            attribute strand_copper_fraction : Real = 0.5 {
                doc /* **Source**: knowledge/sources/critical_current_scaling_and_the_pivot_point_in_nb3sn/raw.pdf **Reference**: Table 1, PDF p.3: Cu/non-Cu 1.0 +/- 0.1 **Basis**: copper fraction of the strand 0.5 [1] **Last Updated**: 2026-09-29 */
            }
            attribute p : Real = 0.578 {
                doc /* **Source**: knowledge/sources/performance_analysis_of_the_toroidal_field_iter_production/raw.pdf **Reference**: Table III, PDF p.24 (images/tmpniti0z1h.pdf-0024-01.png), column WST TFCN5-TFCN6, p **Basis**: ITER TF production median at (12 T, 6.7 K, -0.3 %), transcription confirmed in check-nb3sn.md Recheck r3 items 6-7 **Last Updated**: 2026-09-29 */
            }
            attribute q : Real = 2.211 {
                doc /* **Source**: knowledge/sources/performance_analysis_of_the_toroidal_field_iter_production/raw.pdf **Reference**: Table III, PDF p.24 (images/tmpniti0z1h.pdf-0024-01.png), column WST TFCN5-TFCN6, q **Basis**: ITER TF production median at (12 T, 6.7 K, -0.3 %), transcription confirmed in check-nb3sn.md Recheck r3 items 6-7 **Last Updated**: 2026-09-29 */
            }
            attribute C1 : Real = 20823.0 {
                doc /* **Source**: knowledge/sources/performance_analysis_of_the_toroidal_field_iter_production/raw.pdf **Reference**: Table III, PDF p.24 (images/tmpniti0z1h.pdf-0024-01.png), column WST TFCN5-TFCN6, C1 [A*T per strand] **Basis**: ITER TF production median at (12 T, 6.7 K, -0.3 %), transcription confirmed in check-nb3sn.md Recheck r3 items 6-7 **Last Updated**: 2026-09-29 */
            }
            attribute Ca1 : Real = 47.52 {
                doc /* **Source**: knowledge/sources/performance_analysis_of_the_toroidal_field_iter_production/raw.pdf **Reference**: Table III, PDF p.24 (images/tmpniti0z1h.pdf-0024-01.png), column WST TFCN5-TFCN6, Ca1 **Basis**: ITER TF production median at (12 T, 6.7 K, -0.3 %), transcription confirmed in check-nb3sn.md Recheck r3 items 6-7 **Last Updated**: 2026-09-29 */
            }
            attribute Ca2 : Real = 0.0 {
                doc /* **Source**: knowledge/sources/performance_analysis_of_the_toroidal_field_iter_production/raw.pdf **Reference**: Table III, PDF p.24 (images/tmpniti0z1h.pdf-0024-01.png), column WST TFCN5-TFCN6, Ca2 **Basis**: ITER TF production median at (12 T, 6.7 K, -0.3 %), transcription confirmed in check-nb3sn.md Recheck r3 items 6-7 **Last Updated**: 2026-09-29 */
            }
            attribute eps0a : Real = 0.00218 {
                doc /* **Source**: knowledge/sources/performance_analysis_of_the_toroidal_field_iter_production/raw.pdf **Reference**: Table III, PDF p.24 (images/tmpniti0z1h.pdf-0024-01.png), column WST TFCN5-TFCN6, eps0a (fraction; column label [%] is wrong) **Basis**: ITER TF production median at (12 T, 6.7 K, -0.3 %), transcription confirmed in check-nb3sn.md Recheck r3 items 6-7 **Last Updated**: 2026-09-29 */
            }
            attribute Bc20 : Real = 34.22 {
                doc /* **Source**: knowledge/sources/performance_analysis_of_the_toroidal_field_iter_production/raw.pdf **Reference**: Table III, PDF p.24 (images/tmpniti0z1h.pdf-0024-01.png), column WST TFCN5-TFCN6, Bc0 [T] **Basis**: ITER TF production median at (12 T, 6.7 K, -0.3 %), transcription confirmed in check-nb3sn.md Recheck r3 items 6-7 **Last Updated**: 2026-09-29 */
            }
            attribute Tc0 : Real = 16.26 {
                doc /* **Source**: knowledge/sources/performance_analysis_of_the_toroidal_field_iter_production/raw.pdf **Reference**: Table III, PDF p.24 (images/tmpniti0z1h.pdf-0024-01.png), column WST TFCN5-TFCN6, Tc0 [K] **Basis**: ITER TF production median at (12 T, 6.7 K, -0.3 %), transcription confirmed in check-nb3sn.md Recheck r3 items 6-7 **Last Updated**: 2026-09-29 */
            }
            // Construction: supplied per-turn areas and allowance-rule inputs.
            attribute cabling_factor : Real = 0.97 {
                doc /* **Source**: knowledge/sources/eu_demo_rw_tf_coil_conductor_dematte_bruzzone/raw.pdf **Reference**: output.md:139, cos(theta) = 0.97 cross-section correction **Basis**: construction P calibration (contract section 4) **Last Updated**: 2026-09-29 */
            }
            attribute cable_void : Real = 0.2 {
                doc /* **Source**: knowledge/sources/eu_demo_rw_tf_coil_conductor_dematte_bruzzone/raw.pdf **Reference**: output.md:139, 20 % void fraction of the Rutherford-like flat cable **Basis**: construction P; the 20 % CICC void applied to REBCO is labelled (contract section 4) **Last Updated**: 2026-09-29 */
            }
            attribute cu_space : Real = 908.46615 {
                doc /* **Source**: work/active/WI-099_magnet-conductor-alternatives/reference-case.json **Reference**: nb3sn/rebco.cu_space; make_reference_case.py construction_P **Basis**: [AGENT] reference offer generated by the declared construction rule at the offer reference duty (10 T, anchor D), rounded up to the next 1e-6 mm2 (design D1); supplied and evaluated as given, never resized [mm2] **Last Updated**: 2026-09-29 */
            }
            attribute steel_area : Real = 916.564801 {
                doc /* **Source**: work/active/WI-099_magnet-conductor-alternatives/reference-case.json **Reference**: steel_area; make_reference_case.py construction_P **Basis**: [AGENT] reference offer generated by the declared construction rule at the offer reference duty (10 T, anchor D), rounded up to the next 1e-6 mm2 (design D1); supplied and evaluated as given, never resized [mm2] **Last Updated**: 2026-09-29 */
            }
            attribute misc_area : Real = 96.555744 {
                doc /* **Source**: work/active/WI-099_magnet-conductor-alternatives/reference-case.json **Reference**: misc_area = 1.1077 mm2/kA x I; contract section 4 cooling channel, strip and gaps **Basis**: [AGENT] reference offer generated by the declared construction rule at the offer reference duty (10 T, anchor D), rounded up to the next 1e-6 mm2 (design D1); supplied and evaluated as given, never resized; residual calibrated to EU DEMO layer 1 (check-nb3sn.md Recheck r3 item 1) [mm2] **Last Updated**: 2026-09-29 */
            }
            attribute solder_area : Real = 0.0 {
                doc /* **Source**: work/orchestration/goals/magnet-material-comparison/evidence/comparison-contract.md **Reference**: section 4 A7: REBCO on construction P carries no solder allowance **Basis**: construction P, no solder [mm2] **Last Updated**: 2026-09-29 */
            }
            attribute ins_fraction : Real = 0.237 {
                doc /* **Source**: knowledge/sources/eu_demo_rw_tf_coil_conductor_dematte_bruzzone/raw.pdf **Reference**: per-layer conductor areas: 1 - 406,531/532,656 (check-nb3sn.md section 4) **Basis**: pack-wide fraction; understates insulation for small conductors (noted, not modeled) [1] **Last Updated**: 2026-09-29 */
            }
            attribute J_cu_rule : Real = 93.4 {
                doc /* **Source**: knowledge/sources/eu_demo_rw_tf_coil_conductor_dematte_bruzzone/raw.pdf **Reference**: Table I, p.2: Cu 1123.7 mm2 at 104.95 kA = 93.4 A/mm2 **Basis**: common protection-copper density for both materials (contract N1); variants 100 and 93.4/100 [A/mm2] **Last Updated**: 2026-09-29 */
            }
            attribute cu_void : Real = 0.1 {
                doc /* **Source**: knowledge/sources/eu_demo_rw_tf_coil_conductor_dematte_bruzzone/raw.pdf **Reference**: output.md:106, stabilizer Rutherford cables with 10 % void **Basis**: construction P [1] **Last Updated**: 2026-09-29 */
            }
            attribute cu_per_kA_rule : Real = 0.0 {
                doc /* **Source**: work/orchestration/goals/magnet-material-comparison/evidence/comparison-contract.md **Reference**: section 4; per-kA copper rule used only by construction C **Basis**: inactive under construction P (J_cu_rule > 0) [mm2/kA] **Last Updated**: 2026-09-29 */
            }
            attribute steel_per_kA_rule : Real = 12.66 {
                doc /* **Source**: knowledge/sources/eu_demo_rw_tf_coil_conductor_dematte_bruzzone/raw.pdf **Reference**: pack-average steel 12.66 mm2/kA (check-nb3sn.md section 4) **Basis**: [AGENT] bounded; variants 9.36 (layer 1 manufacturing minimum) and 16.24 (layer 8) [mm2/kA] **Last Updated**: 2026-09-29 */
            }
            attribute B_steel_ref : Real = 12.04 {
                doc /* **Source**: knowledge/sources/eu_demo_rw_tf_coil_conductor_dematte_bruzzone/raw.pdf **Reference**: p.3, B_eff = 12.04 T **Basis**: reference field of the steel rule [T] **Last Updated**: 2026-09-29 */
            }
            attribute steel_B_scaling : Real = 1.0 {
                doc /* **Source**: work/orchestration/goals/magnet-material-comparison/evidence/comparison-contract.md **Reference**: section 4, steel scales with B at fixed geometry (Lorentz load ~ B*I) **Basis**: [AGENT] bounded assumption; 1 = scaling on, variant without scaling = 0 **Last Updated**: 2026-09-29 */
            }
            // Inventory and cost.
            attribute element_density : Real = 8900.0 {
                doc /* **Source**: work/orchestration/goals/magnet-material-comparison/evidence/check-rebco-cryo-cost.md **Reference**: section 6, assumed strand density 8.9 g/cm3 **Basis**: [AGENT] assumed density of the superconducting element, used for mass only; cost is per metre [kg/m3] **Last Updated**: 2026-09-29 */
            }
            attribute rho_cu : Real = 8940.0 {
                doc /* **Source**: knowledge/sources/reliable_source_metals_material_densities/raw.pdf **Reference**: p.1 C101/C110; inherited from models/designs/stellarator_09/stellarator_plant.sysml:380-405 **Basis**: [INHERITED: Stellaris model density] [kg/m3] **Last Updated**: 2026-09-29 */
            }
            attribute rho_steel : Real = 8000.0 {
                doc /* **Source**: knowledge/sources/reliable_source_metals_material_densities/raw.pdf **Reference**: p.1 SS316; inherited from models/designs/stellarator_09/stellarator_plant.sysml:380-405 **Basis**: [INHERITED: Stellaris model density] [kg/m3] **Last Updated**: 2026-09-29 */
            }
            attribute rho_solder : Real = 8390.0 {
                doc /* **Source**: knowledge/sources/indium_corporation_bar_solder_alloy_properties/raw.html **Reference**: :995 Sn63Pb37; inherited from models/designs/stellarator_09/stellarator_plant.sysml:380-405 **Basis**: [INHERITED: Stellaris model density; Sn63Pb37 proxy] [kg/m3] **Last Updated**: 2026-09-29 */
            }
            attribute price_cu : Real = 11.0 {
                doc /* **Source**: /home/reid/1cfe/1costingfe/src/costingfe/data/defaults/costing_constants.yaml (pin 0254385) **Reference**: :49 coil_cu_price_per_kg; inherited from models/designs/stellarator_09/stellarator_plant.sysml:380-405 **Basis**: [INHERITED: Stellaris model price; year unstated] [USD/kg] **Last Updated**: 2026-09-29 */
            }
            attribute price_steel : Real = 6.0 {
                doc /* **Source**: /home/reid/1cfe/1costingfe/src/costingfe/data/defaults/costing_constants.yaml (pin 0254385) **Reference**: :52 coil_steel_price_per_kg; inherited from models/designs/stellarator_09/stellarator_plant.sysml:380-405 **Basis**: [INHERITED: Stellaris model price; year unstated] [USD/kg] **Last Updated**: 2026-09-29 */
            }
            attribute price_solder : Real = 64.44111923663972 {
                doc /* **Source**: knowledge/sources/rotometals_aim_sn63pb37_one_pound_solder_bar_price/raw.html **Reference**: 29.23 USD per pound; inherited from models/designs/stellarator_09/stellarator_plant.sysml:380-405 **Basis**: [INHERITED: Stellaris model retail proxy] [USD/kg] **Last Updated**: 2026-09-29 */
            }
            attribute element_price_per_m : Real = 8.0 {
                doc /* **Source**: knowledge/sources/cooley_and_pong_2016_cost_drivers_for_very_high_energy_p_p/output.md **Reference**: per-kg price 1.5-2 M$/t -> 7.9-10.6 USD2021/m of 0.82 mm strand (check-rebco-cryo-cost.md section 6) **Basis**: reference 8 USD2021/m; range 5.4-13.5 [USD2021/m] **Last Updated**: 2026-09-29 */
            }
            attribute manufacturing_per_m : Real = 0.0 {
                doc /* **Source**: work/orchestration/goals/magnet-material-comparison/evidence/comparison-contract.md **Reference**: section 7 manufacturing-allowance sensitivity (ITER TF 985 USD/m 2014 = 1128 USD/m 2021) **Basis**: [AGENT] reference 0; nonzero only in the manufacturing-allowance variant (design D7) [USD2021 per conductor metre] **Last Updated**: 2026-09-29 */
            }
            // Cold-stage load.
            attribute nuclear_density : Real = 35.5 {
                doc /* **Source**: knowledge/concept_research/09-qi-stellarator-hts/iter-01/sources/stellaris-design-details/images/page_020_table_0.png **Reference**: Stellaris Table 6, 35.5 W/m3 (models/designs/stellarator_09/stellarator_plant.sysml:492) **Basis**: [INHERITED: Stellaris model value], equal for both materials [W/m3] **Last Updated**: 2026-09-29 */
            }
            attribute cold_volume : Real = 473.8507776 {
                doc /* **Source**: knowledge/sources/eu_demo_rw_tf_coil_conductor_dematte_bruzzone/raw.pdf **Reference**: 16 coils x 1.296 m x 0.411 m x 55.6 m turn length; contract section 6 **Basis**: bounded assumption (anchor D envelope volume) [m3] **Last Updated**: 2026-09-29 */
            }
            attribute radiation_ref : Real = 1300.0 {
                doc /* **Source**: knowledge/sources/koncar_et_al_2017_heat_loads_and_design_temperature/ **Reference**: Table 1 base case, PDF pp.4-5 (knowledge/raw/koncar17578.pdf): 1.3 kW radiation from 80 K shields **Basis**: temperature-independent (ratio 0.996); attributed wholly to the TF, bounded upper assumption [W] **Last Updated**: 2026-09-29 */
            }
            attribute conduction_ref : Real = 4600.0 {
                doc /* **Source**: knowledge/sources/koncar_et_al_2017_heat_loads_and_design_temperature/ **Reference**: Table 1 base case: 4.4 kW thermal-anchor + 0.2 kW shield-support conduction **Basis**: bounded upper assumption, scaled by the 316 conductivity integral [W at T_conduction_ref] **Last Updated**: 2026-09-29 */
            }
            attribute T_conduction_ref : Real = 4.0 {
                doc /* **Source**: knowledge/sources/koncar_et_al_2017_heat_loads_and_design_temperature/ **Reference**: Table 1, magnets at 4 K **Basis**: reference cold temperature of conduction_ref [K] **Last Updated**: 2026-09-29 */
            }
            attribute n_leads : Real = 4.0 {
                doc /* **Source**: work/orchestration/goals/magnet-material-comparison/evidence/comparison-contract.md **Reference**: section 6 anchor D, n_leads = 4 **Basis**: bounded assumption [1] **Last Updated**: 2026-09-29 */
            }
            attribute f_lead : Real = 1.25 {
                doc /* **Source**: work/orchestration/goals/magnet-material-comparison/evidence/comparison-contract.md **Reference**: section 6 anchor D, f_lead = 1.25 **Basis**: bounded assumption, excess over the ideal lead [1] **Last Updated**: 2026-09-29 */
            }
            attribute L0 : Real = 2.45e-08 {
                doc /* **Source**: knowledge/sources/current_leads_and_superconducting_links_ballarino_cern/ **Reference**: slide 14 conduction-cooled optimum; reproduces 47 W/kA (check-rebco-cryo-cost.md section 5) **Basis**: Lorenz number [W Ohm/K2] **Last Updated**: 2026-09-29 */
            }
            attribute p_joint_ref : Real = 2819.71264 {
                doc /* **Source**: knowledge/sources/advance_in_the_conceptual_design_of_the_european_demo/raw.pdf **Reference**: output.md:151, 1 nOhm joint requirement; 256 joints = 16 coils x 16 joints at I_ref **Basis**: bounded assumption on joint count: 256 x 1e-9 Ohm x I_ref^2 [W] **Last Updated**: 2026-09-29 */
            }
            attribute I_joint_ref : Real = 104950.0 {
                doc /* **Source**: knowledge/sources/eu_demo_rw_tf_coil_conductor_dematte_bruzzone/raw.pdf **Reference**: 104.95 kA operating current **Basis**: reference current of p_joint_ref [A] **Last Updated**: 2026-09-29 */
            }
            attribute shield_static : Real = 1102000.0 {
                doc /* **Source**: knowledge/sources/koncar_et_al_2017_heat_loads_and_design_temperature/ **Reference**: Table 1 base case, PDF p.5: VVTS 912.6 kW + CTS 189.4 kW = 1102.0 kW; the 1107.9 kW total includes the 5.9 kW magnet load, already in the cold stage (design.md section 7 A6) **Basis**: [AGENT] intercept-stage static load, common to both materials [W] **Last Updated**: 2026-09-29 */
            }
            attribute load_multiplier : Real = 1.0 {
                doc /* **Source**: work/orchestration/goals/magnet-material-comparison/evidence/comparison-contract.md **Reference**: section 6 cold-load multiplier sensitivity 0.5 and 2 **Basis**: reference 1 [1] **Last Updated**: 2026-09-29 */
            }
            // Refrigeration: installed rating and efficiency/capital basis.
            attribute rating_cold : Real = 30000.0 {
                doc /* **Source**: work/active/WI-099_magnet-conductor-alternatives/reference-case.json **Reference**: rating_cold; fixed list 1-75 kW (contract section 5) **Basis**: [AGENT] installed capacity offer: smallest listed rating at or above the reference offer demand; supplied, never set from demand [W] **Last Updated**: 2026-09-29 */
            }
            attribute eta_mode : Real = 0.0 {
                doc /* **Source**: work/orchestration/goals/magnet-material-comparison/evidence/comparison-contract.md **Reference**: section 6: Green eta at the installed cooling capacity **Basis**: reference mode 0; modes 1 (constant) and 2 (input-power basis) are sensitivities **Last Updated**: 2026-09-29 */
            }
            attribute eta_const : Real = 0.24 {
                doc /* **Source**: knowledge/sources/strobridge_1974_cryogenic_refrigerators_an_updated_survey/ **Reference**: Fig. 1 (about 24 % of Carnot at 10 kW); contract section 6 **Basis**: constant-efficiency sensitivity 0.24 [1] **Last Updated**: 2026-09-29 */
            }
            attribute green_a : Real = 0.155 {
                doc /* **Source**: knowledge/sources/green_2015_cost_of_coolers_at_4_2_20_40_and_77_k_publisher/ **Reference**: Eq. 2, printed p.2 (PDF p.3): eta = 15.5 % x R(kW)^0.23 **Basis**: coefficient 0.155 [1] **Last Updated**: 2026-09-29 */
            }
            attribute green_b : Real = 0.23 {
                doc /* **Source**: knowledge/sources/green_2015_cost_of_coolers_at_4_2_20_40_and_77_k_publisher/ **Reference**: Eq. 2, printed p.2 (PDF p.3) **Basis**: exponent 0.23 [1] **Last Updated**: 2026-09-29 */
            }
            attribute f_carnot_shield : Real = 0.2 {
                doc /* **Source**: models/designs/stellarator_09/stellarator_plant.sysml **Reference**: cryoplant f_carnot_shield = 0.20; contract section 6 **Basis**: [INHERITED: Stellaris model fraction of Carnot at 77 K] [1] **Last Updated**: 2026-09-29 */
            }
            attribute capital_mode : Real = 0.0 {
                doc /* **Source**: work/orchestration/goals/magnet-material-comparison/evidence/comparison-contract.md **Reference**: section 6: 20 K capital by input-power equivalence **Basis**: reference mode 0; mode 1 capacity basis is a sensitivity **Last Updated**: 2026-09-29 */
            }
            attribute green_c : Real = 3100000.0 {
                doc /* **Source**: knowledge/sources/green_2015_cost_of_coolers_at_4_2_20_40_and_77_k_publisher/ **Reference**: Eq. 1, printed p.2 (PDF p.3): C = 3.1 M$2015 x R(kW)^0.65 **Basis**: coefficient [USD2015] **Last Updated**: 2026-09-29 */
            }
            attribute green_d : Real = 0.65 {
                doc /* **Source**: knowledge/sources/green_2015_cost_of_coolers_at_4_2_20_40_and_77_k_publisher/ **Reference**: Eq. 1, printed p.2 (PDF p.3) **Basis**: exponent 0.65 [1] **Last Updated**: 2026-09-29 */
            }
            attribute T_green : Real = 4.5 {
                doc /* **Source**: knowledge/sources/green_2015_cost_of_coolers_at_4_2_20_40_and_77_k_publisher/ **Reference**: Eq. 1-2 fitted on 4.5 K refrigerators **Basis**: reference temperature of Green laws [K] **Last Updated**: 2026-09-29 */
            }
            // Fixed design values (not case inputs): law domain, intercept and ambient temperatures, NIST 316 fit.
            attribute B_law_min : Real = 8.0 {
                doc /* **Source**: knowledge/sources/critical_current_scaling_and_the_pivot_point_in_nb3sn/output.md **Reference**: :45 and Figs. 7-9 (8-14.5 T data); contract section 2 **Basis**: fixed design value: lower field of the law domain [T] **Last Updated**: 2026-09-29 */
            }
            attribute B_law_max : Real = 14.5 {
                doc /* **Source**: knowledge/sources/critical_current_scaling_and_the_pivot_point_in_nb3sn/output.md **Reference**: :45, fields to 14.5 T; contract section 2 **Basis**: fixed design value: upper field of the law domain (law-only band 13.5-14.5 T) [T] **Last Updated**: 2026-09-29 */
            }
            attribute B_design_max : Real = 12.2 {
                doc /* **Source**: knowledge/sources/superconductors_for_fusion_a_roadmap_mitchell_et_al_sust/output.md **Reference**: :1055 (p.67), EU DEMO R&W graded pack 12.2 T layer; contract section 2 **Basis**: fixed design value: sourced design range, supported up to 12.2 T [T] **Last Updated**: 2026-09-29 */
            }
            attribute B_edge_max : Real = 13.5 {
                doc /* **Source**: knowledge/sources/design_manufacture_and_test_of_a_82_ka_react_wind_tf/output.md **Reference**: :135, :139, 82.4 kA / 13.5 T design tested to 70 kA; contract section 2 **Basis**: fixed design value: edge band 12.2-13.5 T [T] **Last Updated**: 2026-09-29 */
            }
            attribute T_law_min : Real = 4.2 {
                doc /* **Source**: knowledge/sources/critical_current_scaling_and_the_pivot_point_in_nb3sn/output.md **Reference**: :45, 4.2 <= T <= 12 K **Basis**: fixed design value [K] **Last Updated**: 2026-09-29 */
            }
            attribute T_law_max : Real = 12.0 {
                doc /* **Source**: knowledge/sources/critical_current_scaling_and_the_pivot_point_in_nb3sn/output.md **Reference**: :45, 4.2 <= T <= 12 K **Basis**: fixed design value [K] **Last Updated**: 2026-09-29 */
            }
            attribute eps_min : Real = -0.01 {
                doc /* **Source**: work/orchestration/goals/magnet-material-comparison/evidence/comparison-contract.md **Reference**: section 3 validity: intrinsic strain in [-1.0, +0.2] % (Tsui reversible range, check-nb3sn.md Recheck r3 item 3) **Basis**: fixed design value [fraction] **Last Updated**: 2026-09-29 */
            }
            attribute eps_max : Real = 0.002 {
                doc /* **Source**: work/orchestration/goals/magnet-material-comparison/evidence/comparison-contract.md **Reference**: section 3 validity: intrinsic strain in [-1.0, +0.2] % **Basis**: fixed design value [fraction] **Last Updated**: 2026-09-29 */
            }
            attribute T_shield : Real = 77.0 {
                doc /* **Source**: work/orchestration/goals/magnet-material-comparison/evidence/comparison-contract.md **Reference**: section 6, 77 K intercept stage common to both materials **Basis**: fixed design value, not a case input [K] **Last Updated**: 2026-09-29 */
            }
            attribute T_amb : Real = 300.0 {
                doc /* **Source**: knowledge/sources/strobridge_1974_cryogenic_refrigerators_an_updated_survey/ **Reference**: Eq. 1 with T0 = 300 K; contract section 6 **Basis**: fixed design value, not a case input [K] **Last Updated**: 2026-09-29 */
            }
            attribute k_a : Real = -1.4087 {
                doc /* **Source**: knowledge/sources/nist_316_stainless_cryogenic_material_properties/output.md **Reference**: line 24, 316 stainless thermal conductivity coefficient a **Basis**: fixed design value (NIST fit, data range 4-300 K, 2 % fit error), not a case input [1] **Last Updated**: 2026-09-29 */
            }
            attribute k_b : Real = 1.3982 {
                doc /* **Source**: knowledge/sources/nist_316_stainless_cryogenic_material_properties/output.md **Reference**: line 25, 316 stainless thermal conductivity coefficient b **Basis**: fixed design value (NIST fit, data range 4-300 K, 2 % fit error), not a case input [1] **Last Updated**: 2026-09-29 */
            }
            attribute k_c : Real = 0.2543 {
                doc /* **Source**: knowledge/sources/nist_316_stainless_cryogenic_material_properties/output.md **Reference**: line 26, 316 stainless thermal conductivity coefficient c **Basis**: fixed design value (NIST fit, data range 4-300 K, 2 % fit error), not a case input [1] **Last Updated**: 2026-09-29 */
            }
            attribute k_d : Real = -0.626 {
                doc /* **Source**: knowledge/sources/nist_316_stainless_cryogenic_material_properties/output.md **Reference**: line 27, 316 stainless thermal conductivity coefficient d **Basis**: fixed design value (NIST fit, data range 4-300 K, 2 % fit error), not a case input [1] **Last Updated**: 2026-09-29 */
            }
            attribute k_e : Real = 0.2334 {
                doc /* **Source**: knowledge/sources/nist_316_stainless_cryogenic_material_properties/output.md **Reference**: line 28, 316 stainless thermal conductivity coefficient e **Basis**: fixed design value (NIST fit, data range 4-300 K, 2 % fit error), not a case input [1] **Last Updated**: 2026-09-29 */
            }
            attribute k_f : Real = 0.4256 {
                doc /* **Source**: knowledge/sources/nist_316_stainless_cryogenic_material_properties/output.md **Reference**: line 29, 316 stainless thermal conductivity coefficient f **Basis**: fixed design value (NIST fit, data range 4-300 K, 2 % fit error), not a case input [1] **Last Updated**: 2026-09-29 */
            }
            attribute k_g : Real = -0.4658 {
                doc /* **Source**: knowledge/sources/nist_316_stainless_cryogenic_material_properties/output.md **Reference**: line 30, 316 stainless thermal conductivity coefficient g **Basis**: fixed design value (NIST fit, data range 4-300 K, 2 % fit error), not a case input [1] **Last Updated**: 2026-09-29 */
            }
            attribute k_h : Real = 0.165 {
                doc /* **Source**: knowledge/sources/nist_316_stainless_cryogenic_material_properties/output.md **Reference**: line 31, 316 stainless thermal conductivity coefficient h **Basis**: fixed design value (NIST fit, data range 4-300 K, 2 % fit error), not a case input [1] **Last Updated**: 2026-09-29 */
            }
            attribute k_i : Real = -0.0199 {
                doc /* **Source**: knowledge/sources/nist_316_stainless_cryogenic_material_properties/output.md **Reference**: line 32, 316 stainless thermal conductivity coefficient i **Basis**: fixed design value (NIST fit, data range 4-300 K, 2 % fit error), not a case input [1] **Last Updated**: 2026-09-29 */
            }
            calc conductor : 'Nb3Sn Cable Critical Surface' {
                in n_strands_in = n_elements;
                in strand_diameter_in = strand_diameter;
                in strand_copper_fraction_in = strand_copper_fraction;
                in turn_current_in = duty.turn_current;
                in B_peak_in = duty.B_peak;
                in T_supply_in = T_supply;
                in nuclear_rise_in = nuclear_rise;
                in margin_rise_in = margin_rise;
                in p_in = p;
                in q_in = q;
                in C1_in = C1;
                in Ca1_in = Ca1;
                in Ca2_in = Ca2;
                in eps0a_in = eps0a;
                in Bc20_in = Bc20;
                in Tc0_in = Tc0;
                in fraction_rule_in = fraction_rule;
                in acceptance_rule_in = acceptance_rule;
                in B_law_min_in = B_law_min;
                in B_law_max_in = B_law_max;
                in B_design_max_in = B_design_max;
                in B_edge_max_in = B_edge_max;
                in T_law_min_in = T_law_min;
                in T_law_max_in = T_law_max;
                in eps_min_in = eps_min;
                in eps_max_in = eps_max;
                // eps_intrinsic_in is deliberately left unbound: its entry key is this calc usage input
                // (magnet_subsystem__subsystem__nb3sn__conductor__eps_intrinsic_in, library default 0.0).
                // A negative design literal generates as a constant formula, not an overridable entry point,
                // so the reference value -0.003 is supplied by the case point (implementation-notes.md).
                // **Source**: knowledge/sources/eu_demo_rw_tf_coil_conductor_dematte_bruzzone/raw.pdf **Reference**: p.1 and p.3, R&W design strain -0.3 % (prototypes -0.27 %, -0.33 %) **Basis**: bounded assumption: effective-strain transfer to this strand parameterization (check A); sensitivity -0.6 % [fraction] **Last Updated**: 2026-09-29
            }
            attribute element_area : Real = conductor.element_area_total;
            attribute element_copper_area : Real = conductor.element_copper_area;
            attribute supported : Real = conductor.supported;
            attribute status_code : Real = conductor.status_code;
            attribute acceptance_margin : Real = conductor.acceptance_margin;
            attribute acceptance_pass : Real = conductor.acceptance_pass;
            calc area : 'Winding Turn Area Screen' {
                in turn_current_in = duty.turn_current;
                in B_peak_in = duty.B_peak;
                in available_area_in = duty.available_area;
                in element_area_in = element_area;
                in element_copper_area_in = element_copper_area;
                in cabling_factor_in = cabling_factor;
                in cable_void_in = cable_void;
                in cu_space_in = cu_space;
                in steel_area_in = steel_area;
                in misc_area_in = misc_area;
                in solder_area_in = solder_area;
                in ins_fraction_in = ins_fraction;
                in J_cu_rule_in = J_cu_rule;
                in cu_void_in = cu_void;
                in cu_per_kA_rule_in = cu_per_kA_rule;
                in steel_per_kA_rule_in = steel_per_kA_rule;
                in B_steel_ref_in = B_steel_ref;
                in steel_B_scaling_in = steel_B_scaling;
            }
            attribute fit_margin : Real = area.fit_margin;
            attribute cu_margin : Real = area.cu_margin;
            attribute steel_margin : Real = area.steel_margin;
            attribute fit_pass : Real = area.fit_pass;
            attribute cu_pass : Real = area.cu_pass;
            attribute steel_pass : Real = area.steel_pass;
            calc inventory : 'Winding Inventory and Cost' {
                in n_elements_in = n_elements;
                in element_area_in = element_area;
                in element_density_in = element_density;
                in turns_in = duty.turns;
                in coils_in = duty.coils;
                in turn_length_in = duty.turn_length;
                in turn_current_in = duty.turn_current;
                in cu_space_in = cu_space;
                in cu_void_in = cu_void;
                in steel_area_in = steel_area;
                in solder_area_in = solder_area;
                in rho_cu_in = rho_cu;
                in rho_steel_in = rho_steel;
                in rho_solder_in = rho_solder;
                in price_cu_in = price_cu;
                in price_steel_in = price_steel;
                in price_solder_in = price_solder;
                in element_price_per_m_in = element_price_per_m;
                in manufacturing_per_m_in = manufacturing_per_m;
            }
            attribute element_length : Real = inventory.element_length;
            attribute winding_capital : Real = inventory.winding_capital;
            calc cold_load : 'Magnet Cold Stage Load' {
                in T_supply_in = T_supply;
                in T_shield_in = T_shield;
                in T_amb_in = T_amb;
                in turn_current_in = duty.turn_current;
                in nuclear_density_in = nuclear_density;
                in cold_volume_in = cold_volume;
                in radiation_ref_in = radiation_ref;
                in conduction_ref_in = conduction_ref;
                in T_conduction_ref_in = T_conduction_ref;
                in k_a_in = k_a;
                in k_b_in = k_b;
                in k_c_in = k_c;
                in k_d_in = k_d;
                in k_e_in = k_e;
                in k_f_in = k_f;
                in k_g_in = k_g;
                in k_h_in = k_h;
                in k_i_in = k_i;
                in n_leads_in = n_leads;
                in f_lead_in = f_lead;
                in L0_in = L0;
                in p_joint_ref_in = p_joint_ref;
                in I_joint_ref_in = I_joint_ref;
                in shield_static_in = shield_static;
                in load_multiplier_in = load_multiplier;
            }
            attribute q_cold : Real = cold_load.q_cold;
            attribute q_shield : Real = cold_load.q_shield;
            calc refrigeration : 'Staged Refrigeration Screen' {
                in q_cold_in = q_cold;
                in T_supply_in = T_supply;
                in q_shield_in = q_shield;
                in T_shield_in = T_shield;
                in T_amb_in = T_amb;
                in rating_cold_in = rating_cold;
                in eta_mode_in = eta_mode;
                in eta_const_in = eta_const;
                in green_a_in = green_a;
                in green_b_in = green_b;
                in f_carnot_shield_in = f_carnot_shield;
                in capital_mode_in = capital_mode;
                in green_c_in = green_c;
                in green_d_in = green_d;
                in T_green_in = T_green;
                in usd2015_to_2021_in = economics.usd2015_to_2021;
            }
            attribute refrigerator_capital : Real = refrigeration.refrigerator_capital;
            attribute p_in_total_MW : Real = refrigeration.p_in_total_MW;
            attribute capacity_margin : Real = refrigeration.capacity_margin;
            attribute capacity_pass : Real = refrigeration.capacity_pass;
            calc annualized : 'Subsystem Annualized Cost' {
                in winding_capital_in = winding_capital;
                in refrigerator_capital_in = refrigerator_capital;
                in p_in_total_MW_in = p_in_total_MW;
                in crf_in = economics.crf;
                in hours_in = economics.hours;
                in availability_in = economics.availability;
                in electricity_price_in = economics.electricity_price;
            }
            attribute annualized_cost : Real = annualized.annualized_cost;
            // Every evaluated check passes (acceptance_pass already requires a supported status); design section 2.8.
            attribute all_pass : Real = acceptance_pass * fit_pass * cu_pass * steel_pass * capacity_pass;
            assert constraint acceptance_ok : 'Conductor Acceptance' {
                in supported_in = supported;
                in margin_in = acceptance_margin;
            }
            assert constraint fit_ok : 'Winding Fit' {
                in fit_margin_in = fit_margin;
            }
            assert constraint copper_ok : 'Protection Copper Allowance' {
                in cu_margin_in = cu_margin;
            }
            assert constraint steel_ok : 'Structural Steel Allowance' {
                in steel_margin_in = steel_margin;
            }
            assert constraint capacity_ok : 'Refrigerator Capacity' {
                in capacity_margin_in = capacity_margin;
            }
        }
        part rebco {
            doc /* Supplied REBCO 4 mm x 56 um tape cable, 20 K helium supply, on construction P (common-P reference pairing). Owns its supplied offer (element count, construction areas, temperatures, installed refrigerator rating, prices) and evaluates it; asserts its five constraints. Design defaults are the anchor D reference case at 10 T; all values are overridable case inputs. **Source**: work/active/WI-099_magnet-conductor-alternatives/reference-case.json **Reference**: work/active/WI-099_magnet-conductor-alternatives/design.md sections 3, 4 and 6; work/orchestration/goals/magnet-material-comparison/evidence/comparison-contract.md sections 3-7. **Basis**: [AGENT] reviewed design; MR-7 role record in design section 4. **Last Updated**: 2026-09-29 */
            // Conductor definition and chosen temperatures (design section 6, conductor).
            attribute n_elements : Real = 342.0 {
                doc /* **Source**: work/active/WI-099_magnet-conductor-alternatives/reference-case.json **Reference**: rebco.n_elements **Basis**: [AGENT] reference offer: smallest integer tape count meeting the REBCO fraction rule at the reference duty (contract section 5); supplied, never resized [1] **Last Updated**: 2026-09-29 */
            }
            attribute T_supply : Real = 20.0 {
                doc /* **Source**: work/orchestration/goals/magnet-material-comparison/evidence/comparison-contract.md **Reference**: section 3 REBCO temperatures: supply 20.0 K **Basis**: [AGENT] 20 K helium supply [K] **Last Updated**: 2026-09-29 */
            }
            attribute nuclear_rise : Real = 0.7 {
                doc /* **Source**: knowledge/sources/advance_in_the_conceptual_design_of_the_european_demo/raw.pdf **Reference**: PDF p.3, 0.7 K nuclear rise **Basis**: bounded assumption applied symmetrically to REBCO (contract B4) [K] **Last Updated**: 2026-09-29 */
            }
            attribute margin_rise : Real = 1.5 {
                doc /* **Source**: knowledge/sources/advance_in_the_conceptual_design_of_the_european_demo/raw.pdf **Reference**: PDF p.3, 1.5 K margin **Basis**: symmetric temperature rule 22.2 K (contract section 3) [K] **Last Updated**: 2026-09-29 */
            }
            attribute fraction_rule : Real = 0.8 {
                doc /* **Source**: work/orchestration/goals/magnet-material-comparison/evidence/comparison-contract.md **Reference**: section 3 fraction rule I <= 0.8 Ic **Basis**: [AGENT] existing model convention (WI-062) [1] **Last Updated**: 2026-09-29 */
            }
            attribute acceptance_rule : Real = 1.0 {
                doc /* **Source**: work/orchestration/goals/magnet-material-comparison/evidence/comparison-contract.md **Reference**: section 3 reference acceptance: REBCO fraction rule **Basis**: [AGENT]; 1 = fraction rule **Last Updated**: 2026-09-29 */
            }
            attribute tape_width : Real = 0.004 {
                doc /* **Source**: knowledge/sources/development_and_large_volume_production_of_extremely_high/output.md **Reference**: :113, 4 mm tape (slit from 12 mm) **Basis**: directly supported [m] **Last Updated**: 2026-09-29 */
            }
            attribute tape_thickness : Real = 5.6e-05 {
                doc /* **Source**: knowledge/sources/development_and_large_volume_production_of_extremely_high/output.md **Reference**: :77, :119, total 56 um (40 um substrate, 5 um Cu per side) **Basis**: directly supported [m] **Last Updated**: 2026-09-29 */
            }
            attribute tape_copper_fraction : Real = 0.17857142857142858 {
                doc /* **Source**: knowledge/sources/development_and_large_volume_production_of_extremely_high/output.md **Reference**: :119, electroplated Cu about 5 um per side of 56 um **Basis**: 10/56 of the tape area [1] **Last Updated**: 2026-09-29 */
            }
            attribute anchor_ic : Real = 198.0 {
                doc /* **Source**: knowledge/sources/development_and_large_volume_production_of_extremely_high/output.md **Reference**: :77 (lift factor 1.13) and :137 (lot average 175 A at 77 K, sf) **Basis**: production average 1.13 x 175 A = 198 A per 4 mm tape at 20 T, 20 K, B||c [A] **Last Updated**: 2026-09-29 */
            }
            attribute shape_mode : Real = 0.0 {
                doc /* **Source**: work/orchestration/goals/magnet-material-comparison/evidence/comparison-contract.md **Reference**: section 3: measured 20 K shape (reference) or power law (sensitivity) **Basis**: reference 0 = measured knots **Last Updated**: 2026-09-29 */
            }
            attribute g8 : Real = 2.11 {
                doc /* **Source**: knowledge/sources/development_and_large_volume_production_of_extremely_high/raw.pdf **Reference**: Fig. 1a (p.3), 20 K B||c Geneva curve, Ic(8 T)/Ic(20 T) **Basis**: two independent digitizations agree within 0.01 (check-rebco-cryo-cost.md section 1) [1] **Last Updated**: 2026-09-29 */
            }
            attribute g10 : Real = 1.85 {
                doc /* **Source**: knowledge/sources/development_and_large_volume_production_of_extremely_high/raw.pdf **Reference**: Fig. 1a (p.3), 20 K B||c Geneva curve, Ic(10 T)/Ic(20 T) **Basis**: two independent digitizations agree within 0.01 (check-rebco-cryo-cost.md section 1) [1] **Last Updated**: 2026-09-29 */
            }
            attribute g12 : Real = 1.61 {
                doc /* **Source**: knowledge/sources/development_and_large_volume_production_of_extremely_high/raw.pdf **Reference**: Fig. 1a (p.3), 20 K B||c Geneva curve, Ic(12 T)/Ic(20 T) **Basis**: two independent digitizations agree within 0.01 (check-rebco-cryo-cost.md section 1) [1] **Last Updated**: 2026-09-29 */
            }
            attribute g15 : Real = 1.33 {
                doc /* **Source**: knowledge/sources/development_and_large_volume_production_of_extremely_high/raw.pdf **Reference**: Fig. 1a (p.3), 20 K B||c Geneva curve, Ic(15 T)/Ic(20 T) **Basis**: two independent digitizations agree within 0.01 (check-rebco-cryo-cost.md section 1) [1] **Last Updated**: 2026-09-29 */
            }
            attribute g20 : Real = 1.0 {
                doc /* **Source**: knowledge/sources/development_and_large_volume_production_of_extremely_high/raw.pdf **Reference**: Fig. 1a (p.3), 20 K B||c Geneva curve, Ic(20 T)/Ic(20 T) **Basis**: two independent digitizations agree within 0.01 (check-rebco-cryo-cost.md section 1) [1] **Last Updated**: 2026-09-29 */
            }
            attribute alpha : Real = 0.6 {
                doc /* **Source**: knowledge/sources/development_and_large_volume_production_of_extremely_high/output.md **Reference**: :93, alpha about 0.6 at 20 K **Basis**: power-law sensitivity exponent, the current model law (contract section 3) [1] **Last Updated**: 2026-09-29 */
            }
            attribute T_star : Real = 22.0 {
                doc /* **Source**: knowledge/sources/field_and_temperature_scaling_of_the_critical_current/output.md **Reference**: eq. (1) raw.pdf p.6 form; value from Molodyk Fig. 1a (22.4 K, 21.4 K; check-rebco-cryo-cost.md section 2) **Basis**: reference 22 K; sensitivities 17 and 33 K [K] **Last Updated**: 2026-09-29 */
            }
            attribute degradation : Real = 0.9 {
                doc /* **Source**: knowledge/sources/bruzzone_wesche_uglietti_bykovsky_2016_high_temperature/output.md **Reference**: :101, about 10 % loss after cycling (SuperPower); VIPER < 5 % + 2-4 % **Basis**: retained fraction 0.90; sensitivities 0.80 and 0.95 (contract section 3) [1] **Last Updated**: 2026-09-29 */
            }
            // Construction: supplied per-turn areas and allowance-rule inputs.
            attribute cabling_factor : Real = 0.97 {
                doc /* **Source**: knowledge/sources/eu_demo_rw_tf_coil_conductor_dematte_bruzzone/raw.pdf **Reference**: output.md:139, cos(theta) = 0.97 cross-section correction **Basis**: construction P calibration (contract section 4) **Last Updated**: 2026-09-29 */
            }
            attribute cable_void : Real = 0.2 {
                doc /* **Source**: knowledge/sources/eu_demo_rw_tf_coil_conductor_dematte_bruzzone/raw.pdf **Reference**: output.md:139, 20 % void fraction of the Rutherford-like flat cable **Basis**: construction P; the 20 % CICC void applied to REBCO is labelled (contract section 4) **Last Updated**: 2026-09-29 */
            }
            attribute cu_space : Real = 1021.770903 {
                doc /* **Source**: work/active/WI-099_magnet-conductor-alternatives/reference-case.json **Reference**: nb3sn/rebco.cu_space; make_reference_case.py construction_P **Basis**: [AGENT] reference offer generated by the declared construction rule at the offer reference duty (10 T, anchor D), rounded up to the next 1e-6 mm2 (design D1); supplied and evaluated as given, never resized [mm2] **Last Updated**: 2026-09-29 */
            }
            attribute steel_area : Real = 916.564801 {
                doc /* **Source**: work/active/WI-099_magnet-conductor-alternatives/reference-case.json **Reference**: steel_area; make_reference_case.py construction_P **Basis**: [AGENT] reference offer generated by the declared construction rule at the offer reference duty (10 T, anchor D), rounded up to the next 1e-6 mm2 (design D1); supplied and evaluated as given, never resized [mm2] **Last Updated**: 2026-09-29 */
            }
            attribute misc_area : Real = 96.555744 {
                doc /* **Source**: work/active/WI-099_magnet-conductor-alternatives/reference-case.json **Reference**: misc_area = 1.1077 mm2/kA x I; contract section 4 cooling channel, strip and gaps **Basis**: [AGENT] reference offer generated by the declared construction rule at the offer reference duty (10 T, anchor D), rounded up to the next 1e-6 mm2 (design D1); supplied and evaluated as given, never resized; residual calibrated to EU DEMO layer 1 (check-nb3sn.md Recheck r3 item 1) [mm2] **Last Updated**: 2026-09-29 */
            }
            attribute solder_area : Real = 0.0 {
                doc /* **Source**: work/orchestration/goals/magnet-material-comparison/evidence/comparison-contract.md **Reference**: section 4 A7: REBCO on construction P carries no solder allowance **Basis**: construction P, no solder [mm2] **Last Updated**: 2026-09-29 */
            }
            attribute ins_fraction : Real = 0.237 {
                doc /* **Source**: knowledge/sources/eu_demo_rw_tf_coil_conductor_dematte_bruzzone/raw.pdf **Reference**: per-layer conductor areas: 1 - 406,531/532,656 (check-nb3sn.md section 4) **Basis**: pack-wide fraction; understates insulation for small conductors (noted, not modeled) [1] **Last Updated**: 2026-09-29 */
            }
            attribute J_cu_rule : Real = 93.4 {
                doc /* **Source**: knowledge/sources/eu_demo_rw_tf_coil_conductor_dematte_bruzzone/raw.pdf **Reference**: Table I, p.2: Cu 1123.7 mm2 at 104.95 kA = 93.4 A/mm2 **Basis**: common protection-copper density for both materials (contract N1); variants 100 and 93.4/100 [A/mm2] **Last Updated**: 2026-09-29 */
            }
            attribute cu_void : Real = 0.1 {
                doc /* **Source**: knowledge/sources/eu_demo_rw_tf_coil_conductor_dematte_bruzzone/raw.pdf **Reference**: output.md:106, stabilizer Rutherford cables with 10 % void **Basis**: construction P [1] **Last Updated**: 2026-09-29 */
            }
            attribute cu_per_kA_rule : Real = 0.0 {
                doc /* **Source**: work/orchestration/goals/magnet-material-comparison/evidence/comparison-contract.md **Reference**: section 4; per-kA copper rule used only by construction C **Basis**: inactive under construction P (J_cu_rule > 0) [mm2/kA] **Last Updated**: 2026-09-29 */
            }
            attribute steel_per_kA_rule : Real = 12.66 {
                doc /* **Source**: knowledge/sources/eu_demo_rw_tf_coil_conductor_dematte_bruzzone/raw.pdf **Reference**: pack-average steel 12.66 mm2/kA (check-nb3sn.md section 4) **Basis**: [AGENT] bounded; variants 9.36 (layer 1 manufacturing minimum) and 16.24 (layer 8) [mm2/kA] **Last Updated**: 2026-09-29 */
            }
            attribute B_steel_ref : Real = 12.04 {
                doc /* **Source**: knowledge/sources/eu_demo_rw_tf_coil_conductor_dematte_bruzzone/raw.pdf **Reference**: p.3, B_eff = 12.04 T **Basis**: reference field of the steel rule [T] **Last Updated**: 2026-09-29 */
            }
            attribute steel_B_scaling : Real = 1.0 {
                doc /* **Source**: work/orchestration/goals/magnet-material-comparison/evidence/comparison-contract.md **Reference**: section 4, steel scales with B at fixed geometry (Lorentz load ~ B*I) **Basis**: [AGENT] bounded assumption; 1 = scaling on, variant without scaling = 0 **Last Updated**: 2026-09-29 */
            }
            // Inventory and cost.
            attribute element_density : Real = 8900.0 {
                doc /* **Source**: work/orchestration/goals/magnet-material-comparison/evidence/check-rebco-cryo-cost.md **Reference**: section 6, assumed strand density 8.9 g/cm3 **Basis**: [AGENT] assumed density of the superconducting element, used for mass only; cost is per metre [kg/m3] **Last Updated**: 2026-09-29 */
            }
            attribute rho_cu : Real = 8940.0 {
                doc /* **Source**: knowledge/sources/reliable_source_metals_material_densities/raw.pdf **Reference**: p.1 C101/C110; inherited from models/designs/stellarator_09/stellarator_plant.sysml:380-405 **Basis**: [INHERITED: Stellaris model density] [kg/m3] **Last Updated**: 2026-09-29 */
            }
            attribute rho_steel : Real = 8000.0 {
                doc /* **Source**: knowledge/sources/reliable_source_metals_material_densities/raw.pdf **Reference**: p.1 SS316; inherited from models/designs/stellarator_09/stellarator_plant.sysml:380-405 **Basis**: [INHERITED: Stellaris model density] [kg/m3] **Last Updated**: 2026-09-29 */
            }
            attribute rho_solder : Real = 8390.0 {
                doc /* **Source**: knowledge/sources/indium_corporation_bar_solder_alloy_properties/raw.html **Reference**: :995 Sn63Pb37; inherited from models/designs/stellarator_09/stellarator_plant.sysml:380-405 **Basis**: [INHERITED: Stellaris model density; Sn63Pb37 proxy] [kg/m3] **Last Updated**: 2026-09-29 */
            }
            attribute price_cu : Real = 11.0 {
                doc /* **Source**: /home/reid/1cfe/1costingfe/src/costingfe/data/defaults/costing_constants.yaml (pin 0254385) **Reference**: :49 coil_cu_price_per_kg; inherited from models/designs/stellarator_09/stellarator_plant.sysml:380-405 **Basis**: [INHERITED: Stellaris model price; year unstated] [USD/kg] **Last Updated**: 2026-09-29 */
            }
            attribute price_steel : Real = 6.0 {
                doc /* **Source**: /home/reid/1cfe/1costingfe/src/costingfe/data/defaults/costing_constants.yaml (pin 0254385) **Reference**: :52 coil_steel_price_per_kg; inherited from models/designs/stellarator_09/stellarator_plant.sysml:380-405 **Basis**: [INHERITED: Stellaris model price; year unstated] [USD/kg] **Last Updated**: 2026-09-29 */
            }
            attribute price_solder : Real = 64.44111923663972 {
                doc /* **Source**: knowledge/sources/rotometals_aim_sn63pb37_one_pound_solder_bar_price/raw.html **Reference**: 29.23 USD per pound; inherited from models/designs/stellarator_09/stellarator_plant.sysml:380-405 **Basis**: [INHERITED: Stellaris model retail proxy] [USD/kg] **Last Updated**: 2026-09-29 */
            }
            attribute element_price_per_m : Real = 80.0 {
                doc /* **Source**: knowledge/sources/chislett_mcdonald_surrey_naish_turner_and_hampshire_2022/output.md **Reference**: :191-193 (PDF p.17-18), about 80 USD/kA*m at 6 T, 4.2 K -> 69-100 USD/m; Cooley & Pong 80 USD/m (2016) -> 90 **Basis**: reference 80 USD2021/m, the 2021 market; target 30, volume 10 [USD2021/m] **Last Updated**: 2026-09-29 */
            }
            attribute manufacturing_per_m : Real = 0.0 {
                doc /* **Source**: work/orchestration/goals/magnet-material-comparison/evidence/comparison-contract.md **Reference**: section 7 manufacturing-allowance sensitivity (ITER TF 985 USD/m 2014 = 1128 USD/m 2021) **Basis**: [AGENT] reference 0; nonzero only in the manufacturing-allowance variant (design D7) [USD2021 per conductor metre] **Last Updated**: 2026-09-29 */
            }
            // Cold-stage load.
            attribute nuclear_density : Real = 35.5 {
                doc /* **Source**: knowledge/concept_research/09-qi-stellarator-hts/iter-01/sources/stellaris-design-details/images/page_020_table_0.png **Reference**: Stellaris Table 6, 35.5 W/m3 (models/designs/stellarator_09/stellarator_plant.sysml:492) **Basis**: [INHERITED: Stellaris model value], equal for both materials [W/m3] **Last Updated**: 2026-09-29 */
            }
            attribute cold_volume : Real = 473.8507776 {
                doc /* **Source**: knowledge/sources/eu_demo_rw_tf_coil_conductor_dematte_bruzzone/raw.pdf **Reference**: 16 coils x 1.296 m x 0.411 m x 55.6 m turn length; contract section 6 **Basis**: bounded assumption (anchor D envelope volume) [m3] **Last Updated**: 2026-09-29 */
            }
            attribute radiation_ref : Real = 1300.0 {
                doc /* **Source**: knowledge/sources/koncar_et_al_2017_heat_loads_and_design_temperature/ **Reference**: Table 1 base case, PDF pp.4-5 (knowledge/raw/koncar17578.pdf): 1.3 kW radiation from 80 K shields **Basis**: temperature-independent (ratio 0.996); attributed wholly to the TF, bounded upper assumption [W] **Last Updated**: 2026-09-29 */
            }
            attribute conduction_ref : Real = 4600.0 {
                doc /* **Source**: knowledge/sources/koncar_et_al_2017_heat_loads_and_design_temperature/ **Reference**: Table 1 base case: 4.4 kW thermal-anchor + 0.2 kW shield-support conduction **Basis**: bounded upper assumption, scaled by the 316 conductivity integral [W at T_conduction_ref] **Last Updated**: 2026-09-29 */
            }
            attribute T_conduction_ref : Real = 4.0 {
                doc /* **Source**: knowledge/sources/koncar_et_al_2017_heat_loads_and_design_temperature/ **Reference**: Table 1, magnets at 4 K **Basis**: reference cold temperature of conduction_ref [K] **Last Updated**: 2026-09-29 */
            }
            attribute n_leads : Real = 4.0 {
                doc /* **Source**: work/orchestration/goals/magnet-material-comparison/evidence/comparison-contract.md **Reference**: section 6 anchor D, n_leads = 4 **Basis**: bounded assumption [1] **Last Updated**: 2026-09-29 */
            }
            attribute f_lead : Real = 1.25 {
                doc /* **Source**: work/orchestration/goals/magnet-material-comparison/evidence/comparison-contract.md **Reference**: section 6 anchor D, f_lead = 1.25 **Basis**: bounded assumption, excess over the ideal lead [1] **Last Updated**: 2026-09-29 */
            }
            attribute L0 : Real = 2.45e-08 {
                doc /* **Source**: knowledge/sources/current_leads_and_superconducting_links_ballarino_cern/ **Reference**: slide 14 conduction-cooled optimum; reproduces 47 W/kA (check-rebco-cryo-cost.md section 5) **Basis**: Lorenz number [W Ohm/K2] **Last Updated**: 2026-09-29 */
            }
            attribute p_joint_ref : Real = 2819.71264 {
                doc /* **Source**: knowledge/sources/advance_in_the_conceptual_design_of_the_european_demo/raw.pdf **Reference**: output.md:151, 1 nOhm joint requirement; 256 joints = 16 coils x 16 joints at I_ref **Basis**: bounded assumption on joint count: 256 x 1e-9 Ohm x I_ref^2 [W] **Last Updated**: 2026-09-29 */
            }
            attribute I_joint_ref : Real = 104950.0 {
                doc /* **Source**: knowledge/sources/eu_demo_rw_tf_coil_conductor_dematte_bruzzone/raw.pdf **Reference**: 104.95 kA operating current **Basis**: reference current of p_joint_ref [A] **Last Updated**: 2026-09-29 */
            }
            attribute shield_static : Real = 1102000.0 {
                doc /* **Source**: knowledge/sources/koncar_et_al_2017_heat_loads_and_design_temperature/ **Reference**: Table 1 base case, PDF p.5: VVTS 912.6 kW + CTS 189.4 kW = 1102.0 kW; the 1107.9 kW total includes the 5.9 kW magnet load, already in the cold stage (design.md section 7 A6) **Basis**: [AGENT] intercept-stage static load, common to both materials [W] **Last Updated**: 2026-09-29 */
            }
            attribute load_multiplier : Real = 1.0 {
                doc /* **Source**: work/orchestration/goals/magnet-material-comparison/evidence/comparison-contract.md **Reference**: section 6 cold-load multiplier sensitivity 0.5 and 2 **Basis**: reference 1 [1] **Last Updated**: 2026-09-29 */
            }
            // Refrigeration: installed rating and efficiency/capital basis.
            attribute rating_cold : Real = 30000.0 {
                doc /* **Source**: work/active/WI-099_magnet-conductor-alternatives/reference-case.json **Reference**: rating_cold; fixed list 1-75 kW (contract section 5) **Basis**: [AGENT] installed capacity offer: smallest listed rating at or above the reference offer demand; supplied, never set from demand [W] **Last Updated**: 2026-09-29 */
            }
            attribute eta_mode : Real = 0.0 {
                doc /* **Source**: work/orchestration/goals/magnet-material-comparison/evidence/comparison-contract.md **Reference**: section 6: Green eta at the installed cooling capacity **Basis**: reference mode 0; modes 1 (constant) and 2 (input-power basis) are sensitivities **Last Updated**: 2026-09-29 */
            }
            attribute eta_const : Real = 0.24 {
                doc /* **Source**: knowledge/sources/strobridge_1974_cryogenic_refrigerators_an_updated_survey/ **Reference**: Fig. 1 (about 24 % of Carnot at 10 kW); contract section 6 **Basis**: constant-efficiency sensitivity 0.24 [1] **Last Updated**: 2026-09-29 */
            }
            attribute green_a : Real = 0.155 {
                doc /* **Source**: knowledge/sources/green_2015_cost_of_coolers_at_4_2_20_40_and_77_k_publisher/ **Reference**: Eq. 2, printed p.2 (PDF p.3): eta = 15.5 % x R(kW)^0.23 **Basis**: coefficient 0.155 [1] **Last Updated**: 2026-09-29 */
            }
            attribute green_b : Real = 0.23 {
                doc /* **Source**: knowledge/sources/green_2015_cost_of_coolers_at_4_2_20_40_and_77_k_publisher/ **Reference**: Eq. 2, printed p.2 (PDF p.3) **Basis**: exponent 0.23 [1] **Last Updated**: 2026-09-29 */
            }
            attribute f_carnot_shield : Real = 0.2 {
                doc /* **Source**: models/designs/stellarator_09/stellarator_plant.sysml **Reference**: cryoplant f_carnot_shield = 0.20; contract section 6 **Basis**: [INHERITED: Stellaris model fraction of Carnot at 77 K] [1] **Last Updated**: 2026-09-29 */
            }
            attribute capital_mode : Real = 0.0 {
                doc /* **Source**: work/orchestration/goals/magnet-material-comparison/evidence/comparison-contract.md **Reference**: section 6: 20 K capital by input-power equivalence **Basis**: reference mode 0; mode 1 capacity basis is a sensitivity **Last Updated**: 2026-09-29 */
            }
            attribute green_c : Real = 3100000.0 {
                doc /* **Source**: knowledge/sources/green_2015_cost_of_coolers_at_4_2_20_40_and_77_k_publisher/ **Reference**: Eq. 1, printed p.2 (PDF p.3): C = 3.1 M$2015 x R(kW)^0.65 **Basis**: coefficient [USD2015] **Last Updated**: 2026-09-29 */
            }
            attribute green_d : Real = 0.65 {
                doc /* **Source**: knowledge/sources/green_2015_cost_of_coolers_at_4_2_20_40_and_77_k_publisher/ **Reference**: Eq. 1, printed p.2 (PDF p.3) **Basis**: exponent 0.65 [1] **Last Updated**: 2026-09-29 */
            }
            attribute T_green : Real = 4.5 {
                doc /* **Source**: knowledge/sources/green_2015_cost_of_coolers_at_4_2_20_40_and_77_k_publisher/ **Reference**: Eq. 1-2 fitted on 4.5 K refrigerators **Basis**: reference temperature of Green laws [K] **Last Updated**: 2026-09-29 */
            }
            // Fixed design values (not case inputs): law domain, intercept and ambient temperatures, NIST 316 fit.
            attribute B_knot_min : Real = 8.0 {
                doc /* **Source**: work/orchestration/goals/magnet-material-comparison/evidence/comparison-contract.md **Reference**: section 3 validity: [8, 20] T with the measured shape **Basis**: fixed design value [T] **Last Updated**: 2026-09-29 */
            }
            attribute B_knot_max : Real = 20.0 {
                doc /* **Source**: work/orchestration/goals/magnet-material-comparison/evidence/comparison-contract.md **Reference**: section 3 validity: [8, 20] T with the measured shape **Basis**: fixed design value [T] **Last Updated**: 2026-09-29 */
            }
            attribute B_law_min : Real = 5.0 {
                doc /* **Source**: work/orchestration/goals/magnet-material-comparison/evidence/comparison-contract.md **Reference**: section 3 validity: [5, 24] T for the power-law sensitivity **Basis**: fixed design value [T] **Last Updated**: 2026-09-29 */
            }
            attribute B_law_max : Real = 24.0 {
                doc /* **Source**: work/orchestration/goals/magnet-material-comparison/evidence/comparison-contract.md **Reference**: section 3 validity: [5, 24] T for the power-law sensitivity **Basis**: fixed design value [T] **Last Updated**: 2026-09-29 */
            }
            attribute T_law_min : Real = 4.2 {
                doc /* **Source**: knowledge/sources/field_and_temperature_scaling_of_the_critical_current/output.md **Reference**: :94, exponential law holds to about 50 K at theta = 0 **Basis**: fixed design value [K] **Last Updated**: 2026-09-29 */
            }
            attribute T_law_max : Real = 50.0 {
                doc /* **Source**: knowledge/sources/field_and_temperature_scaling_of_the_critical_current/output.md **Reference**: :94, exponential law holds to about 50 K at theta = 0 **Basis**: fixed design value [K] **Last Updated**: 2026-09-29 */
            }
            attribute T_shield : Real = 77.0 {
                doc /* **Source**: work/orchestration/goals/magnet-material-comparison/evidence/comparison-contract.md **Reference**: section 6, 77 K intercept stage common to both materials **Basis**: fixed design value, not a case input [K] **Last Updated**: 2026-09-29 */
            }
            attribute T_amb : Real = 300.0 {
                doc /* **Source**: knowledge/sources/strobridge_1974_cryogenic_refrigerators_an_updated_survey/ **Reference**: Eq. 1 with T0 = 300 K; contract section 6 **Basis**: fixed design value, not a case input [K] **Last Updated**: 2026-09-29 */
            }
            attribute k_a : Real = -1.4087 {
                doc /* **Source**: knowledge/sources/nist_316_stainless_cryogenic_material_properties/output.md **Reference**: line 24, 316 stainless thermal conductivity coefficient a **Basis**: fixed design value (NIST fit, data range 4-300 K, 2 % fit error), not a case input [1] **Last Updated**: 2026-09-29 */
            }
            attribute k_b : Real = 1.3982 {
                doc /* **Source**: knowledge/sources/nist_316_stainless_cryogenic_material_properties/output.md **Reference**: line 25, 316 stainless thermal conductivity coefficient b **Basis**: fixed design value (NIST fit, data range 4-300 K, 2 % fit error), not a case input [1] **Last Updated**: 2026-09-29 */
            }
            attribute k_c : Real = 0.2543 {
                doc /* **Source**: knowledge/sources/nist_316_stainless_cryogenic_material_properties/output.md **Reference**: line 26, 316 stainless thermal conductivity coefficient c **Basis**: fixed design value (NIST fit, data range 4-300 K, 2 % fit error), not a case input [1] **Last Updated**: 2026-09-29 */
            }
            attribute k_d : Real = -0.626 {
                doc /* **Source**: knowledge/sources/nist_316_stainless_cryogenic_material_properties/output.md **Reference**: line 27, 316 stainless thermal conductivity coefficient d **Basis**: fixed design value (NIST fit, data range 4-300 K, 2 % fit error), not a case input [1] **Last Updated**: 2026-09-29 */
            }
            attribute k_e : Real = 0.2334 {
                doc /* **Source**: knowledge/sources/nist_316_stainless_cryogenic_material_properties/output.md **Reference**: line 28, 316 stainless thermal conductivity coefficient e **Basis**: fixed design value (NIST fit, data range 4-300 K, 2 % fit error), not a case input [1] **Last Updated**: 2026-09-29 */
            }
            attribute k_f : Real = 0.4256 {
                doc /* **Source**: knowledge/sources/nist_316_stainless_cryogenic_material_properties/output.md **Reference**: line 29, 316 stainless thermal conductivity coefficient f **Basis**: fixed design value (NIST fit, data range 4-300 K, 2 % fit error), not a case input [1] **Last Updated**: 2026-09-29 */
            }
            attribute k_g : Real = -0.4658 {
                doc /* **Source**: knowledge/sources/nist_316_stainless_cryogenic_material_properties/output.md **Reference**: line 30, 316 stainless thermal conductivity coefficient g **Basis**: fixed design value (NIST fit, data range 4-300 K, 2 % fit error), not a case input [1] **Last Updated**: 2026-09-29 */
            }
            attribute k_h : Real = 0.165 {
                doc /* **Source**: knowledge/sources/nist_316_stainless_cryogenic_material_properties/output.md **Reference**: line 31, 316 stainless thermal conductivity coefficient h **Basis**: fixed design value (NIST fit, data range 4-300 K, 2 % fit error), not a case input [1] **Last Updated**: 2026-09-29 */
            }
            attribute k_i : Real = -0.0199 {
                doc /* **Source**: knowledge/sources/nist_316_stainless_cryogenic_material_properties/output.md **Reference**: line 32, 316 stainless thermal conductivity coefficient i **Basis**: fixed design value (NIST fit, data range 4-300 K, 2 % fit error), not a case input [1] **Last Updated**: 2026-09-29 */
            }
            calc conductor : 'REBCO Cable Critical Surface' {
                in n_tapes_in = n_elements;
                in tape_width_in = tape_width;
                in tape_thickness_in = tape_thickness;
                in tape_copper_fraction_in = tape_copper_fraction;
                in turn_current_in = duty.turn_current;
                in B_peak_in = duty.B_peak;
                in T_supply_in = T_supply;
                in nuclear_rise_in = nuclear_rise;
                in margin_rise_in = margin_rise;
                in anchor_ic_in = anchor_ic;
                in shape_mode_in = shape_mode;
                in g8_in = g8;
                in g10_in = g10;
                in g12_in = g12;
                in g15_in = g15;
                in g20_in = g20;
                in alpha_in = alpha;
                in T_star_in = T_star;
                in degradation_in = degradation;
                in fraction_rule_in = fraction_rule;
                in acceptance_rule_in = acceptance_rule;
                in B_knot_min_in = B_knot_min;
                in B_knot_max_in = B_knot_max;
                in B_law_min_in = B_law_min;
                in B_law_max_in = B_law_max;
                in T_law_min_in = T_law_min;
                in T_law_max_in = T_law_max;
            }
            attribute element_area : Real = conductor.element_area_total;
            attribute element_copper_area : Real = conductor.element_copper_area;
            attribute supported : Real = conductor.supported;
            attribute status_code : Real = conductor.status_code;
            attribute acceptance_margin : Real = conductor.acceptance_margin;
            attribute acceptance_pass : Real = conductor.acceptance_pass;
            attribute ic_tape_op : Real = conductor.ic_tape_op;
            calc area : 'Winding Turn Area Screen' {
                in turn_current_in = duty.turn_current;
                in B_peak_in = duty.B_peak;
                in available_area_in = duty.available_area;
                in element_area_in = element_area;
                in element_copper_area_in = element_copper_area;
                in cabling_factor_in = cabling_factor;
                in cable_void_in = cable_void;
                in cu_space_in = cu_space;
                in steel_area_in = steel_area;
                in misc_area_in = misc_area;
                in solder_area_in = solder_area;
                in ins_fraction_in = ins_fraction;
                in J_cu_rule_in = J_cu_rule;
                in cu_void_in = cu_void;
                in cu_per_kA_rule_in = cu_per_kA_rule;
                in steel_per_kA_rule_in = steel_per_kA_rule;
                in B_steel_ref_in = B_steel_ref;
                in steel_B_scaling_in = steel_B_scaling;
            }
            attribute fit_margin : Real = area.fit_margin;
            attribute cu_margin : Real = area.cu_margin;
            attribute steel_margin : Real = area.steel_margin;
            attribute fit_pass : Real = area.fit_pass;
            attribute cu_pass : Real = area.cu_pass;
            attribute steel_pass : Real = area.steel_pass;
            calc inventory : 'Winding Inventory and Cost' {
                in n_elements_in = n_elements;
                in element_area_in = element_area;
                in element_density_in = element_density;
                in turns_in = duty.turns;
                in coils_in = duty.coils;
                in turn_length_in = duty.turn_length;
                in turn_current_in = duty.turn_current;
                in cu_space_in = cu_space;
                in cu_void_in = cu_void;
                in steel_area_in = steel_area;
                in solder_area_in = solder_area;
                in rho_cu_in = rho_cu;
                in rho_steel_in = rho_steel;
                in rho_solder_in = rho_solder;
                in price_cu_in = price_cu;
                in price_steel_in = price_steel;
                in price_solder_in = price_solder;
                in element_price_per_m_in = element_price_per_m;
                in manufacturing_per_m_in = manufacturing_per_m;
            }
            attribute element_length : Real = inventory.element_length;
            attribute winding_capital : Real = inventory.winding_capital;
            calc cold_load : 'Magnet Cold Stage Load' {
                in T_supply_in = T_supply;
                in T_shield_in = T_shield;
                in T_amb_in = T_amb;
                in turn_current_in = duty.turn_current;
                in nuclear_density_in = nuclear_density;
                in cold_volume_in = cold_volume;
                in radiation_ref_in = radiation_ref;
                in conduction_ref_in = conduction_ref;
                in T_conduction_ref_in = T_conduction_ref;
                in k_a_in = k_a;
                in k_b_in = k_b;
                in k_c_in = k_c;
                in k_d_in = k_d;
                in k_e_in = k_e;
                in k_f_in = k_f;
                in k_g_in = k_g;
                in k_h_in = k_h;
                in k_i_in = k_i;
                in n_leads_in = n_leads;
                in f_lead_in = f_lead;
                in L0_in = L0;
                in p_joint_ref_in = p_joint_ref;
                in I_joint_ref_in = I_joint_ref;
                in shield_static_in = shield_static;
                in load_multiplier_in = load_multiplier;
            }
            attribute q_cold : Real = cold_load.q_cold;
            attribute q_shield : Real = cold_load.q_shield;
            calc refrigeration : 'Staged Refrigeration Screen' {
                in q_cold_in = q_cold;
                in T_supply_in = T_supply;
                in q_shield_in = q_shield;
                in T_shield_in = T_shield;
                in T_amb_in = T_amb;
                in rating_cold_in = rating_cold;
                in eta_mode_in = eta_mode;
                in eta_const_in = eta_const;
                in green_a_in = green_a;
                in green_b_in = green_b;
                in f_carnot_shield_in = f_carnot_shield;
                in capital_mode_in = capital_mode;
                in green_c_in = green_c;
                in green_d_in = green_d;
                in T_green_in = T_green;
                in usd2015_to_2021_in = economics.usd2015_to_2021;
            }
            attribute refrigerator_capital : Real = refrigeration.refrigerator_capital;
            attribute p_in_total_MW : Real = refrigeration.p_in_total_MW;
            attribute capacity_margin : Real = refrigeration.capacity_margin;
            attribute capacity_pass : Real = refrigeration.capacity_pass;
            calc annualized : 'Subsystem Annualized Cost' {
                in winding_capital_in = winding_capital;
                in refrigerator_capital_in = refrigerator_capital;
                in p_in_total_MW_in = p_in_total_MW;
                in crf_in = economics.crf;
                in hours_in = economics.hours;
                in availability_in = economics.availability;
                in electricity_price_in = economics.electricity_price;
            }
            attribute annualized_cost : Real = annualized.annualized_cost;
            // Every evaluated check passes (acceptance_pass already requires a supported status); design section 2.8.
            attribute all_pass : Real = acceptance_pass * fit_pass * cu_pass * steel_pass * capacity_pass;
            assert constraint acceptance_ok : 'Conductor Acceptance' {
                in supported_in = supported;
                in margin_in = acceptance_margin;
            }
            assert constraint fit_ok : 'Winding Fit' {
                in fit_margin_in = fit_margin;
            }
            assert constraint copper_ok : 'Protection Copper Allowance' {
                in cu_margin_in = cu_margin;
            }
            assert constraint steel_ok : 'Structural Steel Allowance' {
                in steel_margin_in = steel_margin;
            }
            assert constraint capacity_ok : 'Refrigerator Capacity' {
                in capacity_margin_in = capacity_margin;
            }
        }
        calc pair : 'Matched Pair Comparison' {
            in annualized_nb3sn_in = nb3sn.annualized_cost;
            in annualized_rebco_in = rebco.annualized_cost;
            in all_pass_nb3sn_in = nb3sn.all_pass;
            in all_pass_rebco_in = rebco.all_pass;
            in status_nb3sn_in = nb3sn.status_code;
            in status_rebco_in = rebco.status_code;
            in rebco_element_length_in = rebco.element_length;
            in rebco_price_per_m_in = rebco.element_price_per_m;
            in rebco_ic_tape_op_in = rebco.ic_tape_op;
            in crf_in = economics.crf;
        }
    }
}
